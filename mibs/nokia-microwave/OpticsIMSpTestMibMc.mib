OPTICSIM-TEST-MIB DEFINITIONS ::= BEGIN
       IMPORTS
       MODULE-IDENTITY, OBJECT-IDENTITY, OBJECT-TYPE,
       Integer32 FROM SNMPv2-SMI
       DisplayString, InstancePointer FROM SNMPv2-TC
       MODULE-COMPLIANCE, OBJECT-GROUP FROM SNMPv2-CONF
       OpticsIMRadioChannelNumber FROM OPTICSIM-COMMON-TC
       opticsimSdhPdhMib, opticsimSdhPdhMC FROM OPTICSIM-RADIOREG-MIB
	  TruthValue FROM SNMPv2-TC;

 opticsIMTestMib MODULE-IDENTITY
       LAST-UPDATED "202105310000Z"
       ORGANIZATION "Alcatel TND"
       CONTACT-INFO "Alcatel TND"
       DESCRIPTION
                 "SDH/PDH TEST MIB."

       REVISION "202105310000Z"
       DESCRIPTION
	" Added loopbackVlanId and loopbackMacAddressSwap objects to loopbackTable.
	"

       REVISION "201511130000Z"
       DESCRIPTION
	"-SNMPIDL-507, update LAST-UPDATED and REVISION date format adding the 2 digits missing (20) for yers after 1999.
Added a REVISION block corresponding to the LAST-UPDATED timestamp.
       - SNMPIDL-508, added a space between opening and closing braces and the enclosed content.
	"

       REVISION "200805290000Z"
       DESCRIPTION
                 "Added the 'loopAndStop' enum to loopbackBehaviour."
       REVISION "200410200000Z"
	 DESCRIPTION
                 "Added the ActivationDate and the TimeoutPeriod objects to the LoopbackEntry."
       REVISION "200211050000Z"

       DESCRIPTION
                 "Added the RadioChanelNumber object to the LoopbackEntry. Added the LoopbackExtTable 
                  for the loopbacks management on radio link base. "
       REVISION "200207240000Z"
       DESCRIPTION
                " Updated the syntax of loopbackObjectInstanceId object, removed the loopbackObjectClassId 
                  object. "
       REVISION "200205100000Z"
       DESCRIPTION
                "Updated the loopbackTable and added the loopbackAllTribs wildcard. "

       REVISION "200201250000Z"
       DESCRIPTION
                "Initial Release of SDH/PDH TEST MIB."
 ::= {  opticsimSdhPdhMib 4 }


opticsIMTestMibObject      OBJECT IDENTIFIER ::= { opticsIMTestMib 1 }


opticsIMLoopbackTable OBJECT-TYPE
       SYNTAX SEQUENCE OF OpticsIMLoopbackEntry
       MAX-ACCESS				not-accessible
       STATUS						current
       DESCRIPTION
             " According to the equipment configuration, this table contains the list of all the loopbacks points 
               and related activation status (not active or active). "
::= { opticsIMTestMibObject 1 }

opticsIMLoopbackEntry OBJECT-TYPE
       SYNTAX					OpticsIMLoopbackEntry
       MAX-ACCESS			not-accessible
       STATUS					current
       DESCRIPTION
            "An entry of the loopbacks table.
             A loopback point is identified by the TP on which the loopback is performed and by the 
             associated directionality (external line or internal). 
             In order to distinguish more loopback points available on the same TP and with the same 
             directionality, a further string parameter has to be used (loopbackPointAdditionalDefinition).  "
       INDEX   { loopbackRadioChannelNumber, loopbackIndex }
::= { opticsIMLoopbackTable 1 } 

OpticsIMLoopbackEntry ::= SEQUENCE {
   loopbackIndex			Integer32,
   loopbackPointObjectInstance		InstancePointer,
   loopbackDirectionality		INTEGER,
   loopbackPointAdditionalDefinition	DisplayString,
   loopbackBehaviour			INTEGER,
   loopbackActivation			INTEGER,
   loopbackRadioChannelNumber		OpticsIMRadioChannelNumber,
   loopbackActivationDate		DisplayString,
   loopbackTimeoutPeriod		Integer32,
   loopbackVlanId			Integer32,
   loopbackMacAddressSwap		TruthValue
 }

loopbackIndex OBJECT-TYPE
       SYNTAX			Integer32
       MAX-ACCESS	not-accessible
       STATUS			current
       DESCRIPTION
           "This object identifies an index of the table. "
::= { opticsIMLoopbackEntry 1 }

loopbackPointObjectInstance OBJECT-TYPE
       SYNTAX			InstancePointer
       MAX-ACCESS	read-only
       STATUS			current
       DESCRIPTION
           "This object identifies the TP associated to the loopback point. 
            The special value opticsIMLoopbackAllTribs indicates that the loopback has to performed not 
            on a specific TP but on all the object instances of the TPs associated to the tributaries physical 
            ports (i.e. all the e1pPITTP instances). "
::= { opticsIMLoopbackEntry 3 }

loopbackDirectionality OBJECT-TYPE
       SYNTAX INTEGER {
         externalLine (1),
         internal (2) 
         }
       MAX-ACCESS	read-only
       STATUS			current
       DESCRIPTION
           "This object specifies the direction (externalLine or internal) of the loopback. 
            The internal value means that the signal to be looped back is a signal generated by the NE itself,   
            while the externaLine value means that the signal to be looped back is a signal received from the 
            outside line. "
::= { opticsIMLoopbackEntry 4 }

loopbackPointAdditionalDefinition OBJECT-TYPE
       SYNTAX			DisplayString (SIZE(0..10))
       MAX-ACCESS	read-only
       STATUS			current
       DESCRIPTION
           "This object is used to identify a loopback point when more loopback points are available on the 
            same TP (and then identified by the same loopbackPointObjectInstance) and with the same 
            direction. "
::= { opticsIMLoopbackEntry 5 }

loopbackBehaviour OBJECT-TYPE
       SYNTAX INTEGER {
         loopAndContinue (1),
         loopAndAIS (2),
         loopAndStop (3)
         }
       MAX-ACCESS	read-only
       STATUS			current
       DESCRIPTION
           "This object specifies the behaviour of the loopback: loop-And-Continue, loop-And-AIS or loop-And-Stop . 
            If the loopAndContinue value is selected the signal after the loopback is identical to the signal 
            that is being looped back. 
            If  the loopAndAIS value is selected the signal after the loopback is all 1-s (AIS). 
            If  the loopAndStop value is selected the signal after the loopback is not transmitted. "
::= { opticsIMLoopbackEntry 6 }

loopbackActivation OBJECT-TYPE
       SYNTAX INTEGER {
         notActive (1),
         active (2) 
         }
       MAX-ACCESS	read-write
       STATUS			current
       DESCRIPTION
           "This object specifies if the loopback is active or not. "
       DEFVAL { notActive }
::= { opticsIMLoopbackEntry 7 }

loopbackRadioChannelNumber OBJECT-TYPE
     SYNTAX				OpticsIMRadioChannelNumber
     MAX-ACCESS		not-accessible
     STATUS				current
     DESCRIPTION
         "See Textual Conventions."
::= { opticsIMLoopbackEntry 8 }

loopbackActivationDate OBJECT-TYPE
       SYNTAX			DisplayString
       MAX-ACCESS	read-only
       STATUS			current
       DESCRIPTION
           "This object indicates the date and the time when the loopback has been activated.
             It is provided according to the following format: yyy/mm/dd hh:mm:ss.
             If the loopback has not been yet activated, then the string notYetActivated is used." 
::= { opticsIMLoopbackEntry 9 }

loopbackTimeoutPeriod OBJECT-TYPE
       SYNTAX			Integer32 (0..5760)
       MAX-ACCESS	read-write
       STATUS			current
       DESCRIPTION
           "This object indicates the time period, measured in units of minutes, from the activation date
             (specified on loopbackActivationDate object) during the loopback is active.
             After this timeout the agent disables the loopback (notActive value on loopbackActivation)."
::= { opticsIMLoopbackEntry 10 }

loopbackVlanId OBJECT-TYPE
       SYNTAX			Integer32 (0 | 2..4080)
       MAX-ACCESS	read-write
       STATUS			current
       DESCRIPTION
           "This object indicates , in a LoopAndContinue , all traffic is forwarded except one with loopbackVlanId that is looped back.
             Default value for loopbackVlanId is 0, which means no loopbackVlanId assignment and everything is looped back. 
		Any change is allowed only if the loopback has not been yet activated."
::= { opticsIMLoopbackEntry 11 }

loopbackMacAddressSwap OBJECT-TYPE
       SYNTAX			TruthValue
       MAX-ACCESS	read-write
       STATUS			current
       DESCRIPTION
           "This object indicates if the MAC address of Ethernet frames are swapped before being loop backed.
		Any change is allowed only if the loopback has not been yet activated"
::= { opticsIMLoopbackEntry 12 }

---
---

opticsIMLoopbackAllTribs OBJECT-IDENTITY
       STATUS					current
       DESCRIPTION
             "This value is used, inside loopbackPointObjectInstance, as wildcard value in order to indicate 
              that the loopback is performed on all the tributaries. "
::= { opticsIMTestMibObject 2 }


opticsIMLoopbackExtTable OBJECT-TYPE
       SYNTAX SEQUENCE OF OpticsIMLoopbackExtEntry
       MAX-ACCESS				not-accessible
       STATUS						current
       DESCRIPTION
            " This table represents an extension of the opticsIMLoopbackTable. It is used to allow a 
              loopbacks management on radio link base: the managing system can manage not only the Near 
              End loopbacks but, according to the types of loopback supported by each type of NE, also the 
              Far End ones.  "
::= { opticsIMTestMibObject 3 }

opticsIMLoopbackExtEntry OBJECT-TYPE
       SYNTAX					OpticsIMLoopbackExtEntry
       MAX-ACCESS			not-accessible
       STATUS					current
       DESCRIPTION
            "An entry of the opticsIMLoopbackExtTable. "
       INDEX   { loopbackRadioChannelNumber, loopbackIndex }
::= { opticsIMLoopbackExtTable 1 } 

OpticsIMLoopbackExtEntry ::= SEQUENCE {
   loopbackNEType					INTEGER,
   loopbackAllowedManager		INTEGER
  }

loopbackNEType OBJECT-TYPE
       SYNTAX INTEGER {
         nearEnd (1),
         farEnd (2) 
         }
       MAX-ACCESS	read-only
       STATUS			current
       DESCRIPTION
           "This object specifies if the loopback is referred to the Near-End or Far-End NE. "
::= { opticsIMLoopbackExtEntry 1 }

loopbackAllowedManager OBJECT-TYPE
       SYNTAX INTEGER {
         localManager (1),
         everyManager (2) 
         }
       MAX-ACCESS	read-only
       STATUS			current
       DESCRIPTION
           "This object specifies if the loopback activation can be requested only by the local manager or by 
            every type of manager, local or remote. "
::= { opticsIMLoopbackExtEntry 2 }





-- OPTICSIM-TEST-MC DEFINITIONS ::= BEGIN
--       IMPORTS
--       MODULE-IDENTITY, OBJECT-TYPE, OBJECT-IDENTITY FROM SNMPv2-SMI
--       MODULE-COMPLIANCE, NOTIFICATION-GROUP, OBJECT-GROUP FROM SNMPv2-CONF
--       opticsimSdhPdhMC FROM OPTICSIM-RADIOREG-MIB;


-- opticsIMTestMCCompl MODULE-IDENTITY
--       LAST-UPDATED "0207240000Z"
--       ORGANIZATION "Alcatel TND"
--       CONTACT-INFO "Alcatel TND"
--       DESCRIPTION
--              “ Removed the loopbackObjectClassId object from opticsIMLoopbackGroup. “
--       REVISION "0205100000Z"
--       DESCRIPTION
--              “ Updated the loopback group. “
--       REVISION "0201250000Z"
--       DESCRIPTION 
--           "Initial Release of Test Module Compliance."
    
-- ::= { opticsIMTestMCConf 1 }

opticsIMTestMCConf         OBJECT IDENTIFIER ::= { opticsimSdhPdhMC 4 }
opticsIMTestMCCompl      OBJECT IDENTIFIER ::= { opticsIMTestMCConf 1 }
opticsIMTestMCGroup      OBJECT IDENTIFIER ::= { opticsIMTestMCConf 2 }

opticsIMTestMc MODULE-COMPLIANCE
      STATUS current
      DESCRIPTION 
          "This module compliance describes a set of objects required for Optics-IM Agent 
            implementation. These objects are defined inside opticsIMTestMib. "

       MODULE -- opticsIMTestMib  

MANDATORY-GROUPS { opticsIMLoopbackGroup }

::= { opticsIMTestMCCompl 1 }


opticsIMLoopbackGroup OBJECT-GROUP
      OBJECTS { loopbackPointObjectInstance,
                          loopbackDirectionality,
                          loopbackPointAdditionalDefinition,
                          loopbackBehaviour,
                          loopbackActivation,
                          loopbackActivationDate,
                          loopbackTimeoutPeriod
                          }
      STATUS current 
      DESCRIPTION 
          " This group describes the loopback objects." 
::= { opticsIMTestMCGroup 1 }


opticsIMOptLoopbackLCExtGroup OBJECT-GROUP
      OBJECTS { loopbackNEType,
                          loopbackAllowedManager
                          }
      STATUS current 
      DESCRIPTION 
          " This group describes the loopback objects extension." 
::= { opticsIMTestMCGroup 2 }


END
