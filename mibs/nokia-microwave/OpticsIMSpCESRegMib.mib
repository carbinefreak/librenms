-- "CONFIDENTIAL. All rights reserved. Alcatel. This computer program is protected under Copyright. 
-- Recipient is to retain the program in confidence, and is not permitted to copy, use, distribute, modify or 
-- translate the program without authorization. Passing on and copying,use and communication of its
-- contents is not permitted without written authorization."

OPTICSIM-CESREG-MIB DEFINITIONS ::= BEGIN
    IMPORTS
    MODULE-IDENTITY FROM SNMPv2-SMI
    opticsimEthMib FROM OPTICSIM-ETHREG-MIB ;

opticsimCESMib  MODULE-IDENTITY
    LAST-UPDATED "0610190000Z" 	--  October 19, 2006 
    ORGANIZATION "Alcatel TND"
    CONTACT-INFO "Alcatel TND"
    DESCRIPTION
        "Initial Release OPTICS-IM Circuit Emulation Service REGISTRATION MODULE"
::= { opticsimEthMib 100 }

END
