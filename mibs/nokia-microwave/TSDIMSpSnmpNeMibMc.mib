TSDIM-SNMPNE-MIB DEFINITIONS ::= BEGIN
IMPORTS
  MODULE-IDENTITY, OBJECT-TYPE, IpAddress, NOTIFICATION-TYPE, 
    Unsigned32, Integer32, Gauge32 , Counter32           FROM SNMPv2-SMI
  TEXTUAL-CONVENTION, TruthValue, DisplayString, DateAndTime, 
    RowStatus, PhysAddress, MacAddress                  FROM SNMPv2-TC
    TsdimUdpPort, TsdimManagerType, SLValue, TsdimEventTimeInt, OpticsIMUserLabel
                                                        FROM TSDIM-SNMP-TC
    tsdimEventObjectClassIdentifier, tsdimEventObjectInstanceIdentifier,
    tsdimAlarmSeverity,tsdimAlarmSpecProblem, tsdimEventNotificationId,
    tsdimEventTime, opticsIMAdditionalText, opticsIMAlarmType, InetAddressIPv6 FROM TSDIM-SUPPORT-MIB
    MODULE-COMPLIANCE, NOTIFICATION-GROUP, OBJECT-GROUP FROM SNMPv2-CONF
    ifIndex, InterfaceIndex                             FROM IF-MIB
    IANAifType                                          FROM IANAifType-MIB
    OpticsIMPmPeriodTime                                FROM OPTICSIM-COMMON-TC
    tsdimBasicMib,tsdimBasicMC                          FROM TSDIM-BASICREG-MIB
--    InetAddressIPv6                                     FROM INET-ADDRESS-MIB
;

tsdimSnmpNEMib MODULE-IDENTITY
  LAST-UPDATED "202402270000Z"
    ORGANIZATION "Alcatel OND"
    CONTACT-INFO "Alcatel OND"
    DESCRIPTION
	"TSD-IM SNMP NE MIB "

  REVISION "202402270000Z"
  DESCRIPTION 
	"- Updated some mistakes for wrong sequence definition on the followig table:
		-- opticsIMMngInterfaceListTable
		-- opticsIMIfTable
		-- opticsIMSdhIfTable
		-- opticsIMIfQueueTable 
		-- opticsIMRateLimitingProfileTable

      - Added new probable cause: 				opticsIMAlarmPowerSavingActiveRaise/Clear

	- Added new scalar object:
		opticsIMMaintenanceMode 
  
   	"

  REVISION "202212120000Z"
  DESCRIPTION 
	"- Added new probable cause: opticsIMAlarmLossOfContinuityRaise/Clear
   	"

  REVISION "202208310000Z"
  DESCRIPTION 
	"- for a bug removed line 8294 (opticsIMConditionalSelfTestFai word 
	- removed probable cause opticsIMAlarmInitialPasswordResetRaise/Clear (no more implemented)
   	"

  REVISION "202206150000Z"
  DESCRIPTION
	"Added new probable cause:
        - opticsIMAlarmInitialPasswordResetRaise/Clear.
   	"

  REVISION "202111190000Z"
  DESCRIPTION
	"Update the name of a probable cause:
	from opticsIMAlarmACMDegradefClear to opticsIMAlarmACMDegradeClear (removing an useful 'f' character inside).
   	"

  REVISION "202105310000Z"
  DESCRIPTION
	"Added new probable cause:
        - opticsIMAlarmLocalAutoTxMuteRaise/Clear.
   	"

  REVISION "202104220000Z"
  DESCRIPTION
	"Added new scalar object:
       - opticsIMIfQueueWREDAdminStatus 
   	"
  REVISION "202101150000Z"
  DESCRIPTION
	"Added new probable cause:
       - opticsIMAlarmACMDegradeRaise/Clear
   	"

  REVISION "202012140000Z"
  DESCRIPTION
	"Added new probable cause:
       - opticsIMAlarmMissingDiversityAlignConfRaise/Clear
   	"
  
  REVISION "202011230000Z"
  DESCRIPTION
	"Added new probable cause:
       - opticsIMAlarmVESListenerConnectionFailureRaise/Clear
   	"

  REVISION "202007210000Z"
  DESCRIPTION
	"Added new probable causes:
       - opticsIMAlarmUpdateIPSecKeysFailRaise/Clear
       - opticsIMAlarmZeroizeIPSecKeysFailRaise/Clear
   	"
  
  REVISION "202006080000Z"
  DESCRIPTION
	"Added new probable causes:
       - opticsIMAlarmSecureModeMismatchRaise/Clear
       - opticsIMAlarmSWDLConditionalSelfTestFailRaise/Clear
	  - opticsIMAlarmCRNGConditionalSelfTestFailRaise/Clear 
   	"

  REVISION "202001290000Z"
  DESCRIPTION
	"Added new probable cause:
       - opticsIMAlarmEthOAMUnexpectedCcmConnectivityRaise/Clear
   	"
  REVISION "201911070000Z"
  DESCRIPTION
	"Added new probable cause:
       - opticsIMAlarmSecureSelfTestFailureRaise/Clear
       - opticsIMAlarmIpsecPskMissingRaise/Clear
       - opticsIMAlarmIpsecTunnelSetupFailureRaise/Clear
   	"
  REVISION "201910100000Z"
  DESCRIPTION
	"Added new probable cause:
       - opticsIMAlarmLogUploadFailureRaise/Clear
   	"
  REVISION "201907020000Z"
  DESCRIPTION
	"Added new probable causes:
       - opticsIMAlarmEthOAMUnexpectedMepRaise/Clear
       - opticsIMAlarmEthOAMMACStatusDefectRaise/Clear
   	"
  REVISION "201812180000Z"
  DESCRIPTION
	"Changed probable causes name:
	 - opticsIMAlarmLicenseToBeProvisionedRaise/Clear  to opticsimFreeLicenseRunningRaise/Clear 
         - opticsIMAlarmConfigBlockedForLicenseMissingRaise/Clear to opticsimFreeLicenseExpiredRaise/Clear
   	"

  REVISION "201810160000Z"
  DESCRIPTION
	"added  new probable cause 	opticsIMAlarmStolenStatusRaise/Clear.
   
	"

  REVISION "201803280000Z"
  DESCRIPTION
	"added  new probable causes 	opticsIMAlarmLicenseToBeProvisionedRaise/Clear and opticsIMAlarmConfigBlockedForLicenseMissingRaise/Clear
   
	"

  REVISION "201605060000Z"
  DESCRIPTION
	"- SNMPIDL-518:
        added  new probable causes 	opticsimAlarmCKMRaise/Clear, opticsimAlarmNKMRaise/Clear, 	opticsimAlarmAesFipsFailureRaise/Clear,
	opticsimAlarmSessionTimeoutRaise/Clear, opticsimAlarmESMRaise/Clear, opticsimAlarmKeyUnavailableRaise/Clear.   
	- SNMPIDL-513:
        added new probable causes opticsimThresholdOutputPowerHighRaise/Clear, opticsimThresholdOutputPowerLowRaise/Clear, opticsimThresholdInputPowerHighRaise/Clear,
        opticsimThresholdInputPowerLowRaise/Clear, opticsimInputPowerOverloadRaise/Clear
	"

  REVISION "201509040000Z"
    DESCRIPTION
	"- SNMPIDL-498:
        added  new probable causes 	opticsimAlarm1588TCFailRaise /Clear
     opticsimAlarmTrafficDownRaise /Clear
     opticsimAlarmTrafficLossRaise /Clear
     opticsimAlarmRxProblemRaise /Clear
     opticsimAlarmTxProblemRaise /Clear
     opticsimAlarmLagPortDownRaise /Clear
	"

  REVISION "201505220000Z"
    DESCRIPTION
	"- SNMPIDL-493 :
         Changed label of   opticsimAlarmLicenseMismatchRaise/Clear probable cause to            opticsIMMemoryCardForbiddenToUseRaise /Clear leaving the same   object registration (OID).
       - SNMPIDL-494 :
        Added  opticsIMIf1588TCStatus	new object to opticsIMIfTable 
	"
 
  REVISION "201410090000Z"
  DESCRIPTION
	"SNMPIDL-483 :
         Added opticsimAlarmLossOfPktSynchronizationRaise /Clear
         and opticsimAlarmExcessiveMissingPktRaise /Clear
	"

  REVISION "201405090000Z"
  DESCRIPTION
	"OPTnm26383 : Michael Qiu
         Added opticsIMAlarm1588AnnouncePktLOSRaise/Clear
         opticsIMAlarm1588SyncPktLOS/Clear, opticsIMAlarm1588DelayRespPktLOSRaise/Clear, opticsIMAlarm1588PTPClockclassDEGRaise/Clear
	 and opticsIMAlarmESMCPktLosRaise/Clear
	"

  REVISION "201404070000Z"    
  DESCRIPTION
	"OPTnm26601: C.Addeo
         	Added opticsIMAlarmRemoteFaultIndicationRaise/Clear probable cause.
  	 OPTnm26385: 
         	Added opticsIMAlarmServiceSelectiveDropRaise/Clear probable cause. 
	 OPTnm26463: Alessandra Rossi
         	Added opticsimAlarmlnkaggExBandwidthDegradeRaise/Clear probable cause.
	 	Added object 'opticsIMIflnkaggThreshold' in opticsIMIfTable       
        "
     
  REVISION "201401060000Z"    
  DESCRIPTION
  	"OPTnm23953: Paolo Boccadoro
         Added object 'opticsIMIfAlarmReeval' in opticsIMIfTable.
 	 OPTnm20039: Michael Qiu
   	     Added 'opticsIMIfIpIntfPointer' in opticsIMIfTable.
     OPTnm24314: Paolo Boccadoro 
         Added opticsIMAlarmLoopbackPresenceRaise/Clear probable cause.        
    "
          
  REVISION "201206080000Z"    
  DESCRIPTION    
      "ONDnm09836 and ONDnm09842: P.Villa.
           Added opticsIMNeOverClockedModeEnable, opticsIMNeAlarmAdmin, opticsIMIfPortAlarmAdmin
       OPTnm10120: D.Spreafico.
	   added -- tsdimSnmpAgtIPv6Address, 
                 -- opticsIMMainNTPServerIPv6Address  and  
                 -- opticsIMSpareNTPServerIPv6Address scalar objects
		 -- opticsIMAlarmDuplicatedAddressDetectedRaise/Clear alarms.
       "

  REVISION "201204120000Z"
  DESCRIPTION
      "Daniela Spreafico.
       OPTnm07660:
	   added -- opticsIMTACACSServerManagement tree with 
                  	- opticsIMTACACSServerTable
                  	- opticsIMTACACSLastServerUsed
                  	- opticsIMTACACSAuthentication
          
       OPTnm08359:
	   added  -- opticsIMRateLimitingProfileTable

	   " 
	   
    REVISION    "201201260000Z"
    DESCRIPTION
     "OPTnm05227: Daniela Spreafico.
	   Added  opticsIMUserlabel  on opticsIMIfTable .
	   " 
	   
    REVISION    "201111030000Z"
    DESCRIPTION
     "OPTnm02313: Wang Yun/Wang Fen.
	   Added  opticsIMSwitchTable and opticsIMSwitchPortTable for multi-bridge modle ,
	   added opticsIMIfSwitchId object to opticsIMIfTable .
	   " 
	   
    REVISION    "201106210000Z" 
    DESCRIPTION
     "TSDnm96257: M.Gallina.
	   Added  opticsIMPortCapabilityIndex to opticsIMIfTable 
	   and opticsIMCapabilityProfileTable
	   " 
    
	   
    REVISION    "201105200000Z"
    DESCRIPTION
        "TSDnm93155: Linhai Qiu
	 Added opticsIMIfUnknownMulticastLimit.

         TSDnm91919: D.Spreafico
         Added opticsIMIfQueueSize and opticsIMIfQueueDefaultSize objects to opticsIMIfQueueTable.
 "

    REVISION "201104080000Z"	
    DESCRIPTION 
        "TSDnm91916: D.Spreafico.
	   Added opticsIMAlarmBandwidthDegradeForProtectionSwitchRaise/Clear probable cause.
         "
   
    REVISION "201011260000Z"
    DESCRIPTION 
        "D.Spreafico
	 Added opticsIMIfAvailableBandwidth and opticsIMIfNetBandwidth object to opticsIMIfTable

         P.Villa
         Change granularity [from Megabits per second (Mbps) to Kbps
         (Kilobits per second)] inside DESCRIPTION of opticsIMIfBroadcastTrafficLimit, 
         opticsIMIfMulticastTrafficLimit, opticsIMIfUnknownUnicastTrafficLimit"

    REVISION "201009300000Z"
    DESCRIPTION 
        "D.Spreafico
	 Added incompatibleProtectionRaise/Clear alarms"

    REVISION "201007160000Z"
    DESCRIPTION 
        "TSDnm83904 - P.Villa
	 Added opticsIMIfBroadcastTrafficLimit, 
	       opticsIMIfMulticastTrafficLimit, 
               opticsIMIfUnknownUnicastTrafficLimit"

    REVISION "201006170000Z"
    DESCRIPTION
       "Ma Xiaohua:
         Added the following alarms:
	   opticsIMAlarmInvalidTdmDataRaise/Clear
	"
    REVISION "201005130000Z"
    DESCRIPTION
       "Q.Machael:
         Added the following alarms:
	   opticsIMAlarm1PpsTodLOSRaise/Clear,
           opticsIMAlarm1PpsToDDEGRaise/Clear,
           opticsIMAlarmPtpLossOfLockRaise/Clear,
           opticsIMAlarmPtpFaultyRaise/Clear
	"
    REVISION "201004010000Z"
    DESCRIPTION
       "D.Spreafico: 
         Added new alarm (opticsIMAlarmLossOfESMCRaise/Clear)
        X.Ma:
        Added new alarms for CES:
         opticsIMAlarmStraypacketsRaise
         opticsIMAlarmStraypacketsClear
	 opticsIMAlarmExcessivepacketLossRaise
         opticsIMAlarmExcessivepacketLossClear
         opticsIMAlarmRemotepacketlossRaise
         opticsIMAlarmRemotepacketlossClear
       "
    REVISION "201002050000Z"
    DESCRIPTION
       "P.Villa: TSDnm77715.
        Redefined behavior of existing attribute (opticsIMIfOffsetEgressShapingSize)
        Added new attribute (opticsIMNeFrameSizeMode)

        G.Turner: TSDnm76841.
        Insertion of the opticsIMCfmStatus:
	this scalar object modifies the global enable status of CFM."

  REVISION "200912170000Z"
  DESCRIPTION
       "S. Torassa:
          Addition of the following objects:
	  - opticsimLinkOAMLogMinInterval
        D.Spreafico:
          Addition of the following values to opticsIMIfDemarcRole on 
            opticsIMIfTable:
            internalTraffic (5), 
            internalPower (6), 
            equipmentPower (7)
	    
            URD and URUS alarms trap has been added.

        P.Villa:
	  Added opticsIMNeSyncEthEnable
          Added opticsIMIfLPTSendControl,opticsIMIfLPTCsfConsequentActions,
            opticsIMIfLPTSsfConsequentActions,opticsIMIfLPTHoldOffTime 
       "
  REVISION "200911120000Z"
  DESCRIPTION
    "S.Torassa:
       Addition of the following alarm:
         opticsimAlarmExSERRaise(165)
	 opticsimAlarmExSERClear(166)
     D.Spreafico:
       Addition of the following alarms:
         opticsimAlarmLossOfCESEthFrameRaise(167)
	 opticsimAlarmLossOfCESEthFrameClear(168)
         opticsimAlarmLossOfProtectionRaise(169)
	 opticsimAlarmLossOfProtectionClear(170)
	 opticsimAlarmAisTxRaise(171)
	 opticsimAlarmAisTxClear(172)
	 opticsimAlarmAisRxRaise(173)
	 opticsimAlarmAisRxClear(174)
     P.Villa:
       Added opticsIMNeAlarmsTable"

  REVISION "200909300000Z"
  DESCRIPTION
    "G.Turner:
      Addition of the following alarm:
        (1) opticsimAlarmEthOAMVSFRaise (163)/opticsimAlarmEthOAMVSFClear(164)"

  REVISION "200908060000Z"
  DESCRIPTION
    "Modified OpticsIMHashingKeyList
     Added opticsIMIfPIPMacAddress, opticsIMIfMCEnable
     Added opticsimAlarmFailureOfProtocolProvisioningMismatchRaise,
           opticsimAlarmFailureOfProtocolProvisioningMismatchClear,
           opticsimAlarmFailureOfProtocolTimeOutRaise,
           opticsimAlarmFailureOfProtocolTimeOutClear
           opticsimAlarmLoopingFrameEventRaise, 
           opticsimAlarmLoopingFrameEventClear,
           opticsimAlarmEthOAMMIPOverflowEventRaise,
           opticsimAlarmEthOAMMIPOverflowEventClear,
           opticsimAlarmMcastTableOverflowEventRaise,
           opticsimAlarmMcastTableOverflowEventClear"

  REVISION "200904230000Z"
  DESCRIPTION 
    "S.Torassa:
       Addition of the following objects:
       - opticsIMIfPdhRate
       - opticsimLinkOAMLogMinInterval
       Addition of opticsIMIfOffsetEgressShapingSize attribute 
       Addition of the following alarms:
        (1) opticsimAlarmEthFOPCMRaise (123)/opticsimAlarmEthFOPCMClear(124)
        (2) opticsimAlarmEthFOPPMRaise (125)/opticsimAlarmEthFOPPMClear(126)
        (3) opticsimAlarmEthFOPNRRaise (127)/opticsimAlarmEthFOPNRClear(128)
        (4) opticsimAlarmEthFOPAMRaise (129)/opticsimAlarmEthFOPAMClear(130) 
        (5) opticsimAlarmEthFOPDMRaise (131)/opticsimAlarmEthFOPDMClear(132)
        (6) opticsimAlarmEthNOSYNCRaise (133)/opticsimAlarmEthNOSYNCClear(134)
        (7) opticsimAlarmEthANMRaise (135)/opticsimAlarmEthANMClear(136)
        (8) opticsimAlarmHldOverRaise (137)/opticsimAlarmHldOverClear(138)
        (9) opticsimTLURaise (139)/opticsimTLUClear(140)
        (10) OpticsimAlarmPDHTLCRRaise(141) / OpticsimAlarmPDHTLCRClear (142)
        (11) OpticsimAlarmPDHTLCTRaise(143) / OpticsimAlarmPDHTLCTClear (144)
        (12) OpticsimAlarmPDHPLCTRaise(145) / OpticsimAlarmPDHPLCTClear (146)
        (13) OpticsimAlarmPDHPLCRRaise(147) / OpticsimAlarmPDHPLCRClear (148)
        (14) OpticsimAlarmPDHMNDRaise(149) / OpticsimAlarmPDHMNDClear (150)   
     
     Linhai Qiu
     D.Spreafico:
       Added  new alarm OpticsIMRetimingBufferOverflowRaise(151)/Clear (152)"    
     
  REVISION "200812180000Z"  
  DESCRIPTION 
    "Addition of the following scalar object:
     - opticsimTopologyGroup
     Added  new alarm opticsimAlarmAutomaticEthShutdownRaise/Clear"     

  REVISION "200809040000Z"  
  DESCRIPTION 
    "Addition of the following alarms:
     - opticsimAlarmEthPNACRaise/Clear
     Linhai Qiu

     The following alarms have been added:
       opticsimAlarmEthPNACRaise/Clear"

  REVISION "200808070000Z"   
  DESCRIPTION 
    "Addition of the following alarms:
     - opticsimAlarmEthOAMUNPrRaise/Clear
     Linhai Qiu
       The following alarms have been added:
         opticsimAlarmEthOAMUNPrRaise
         opticsimAlarmEthOAMUNPrClear"

  REVISION "200805290000Z"   
  DESCRIPTION 
    "Duplication of PortList definition for permitting the IDL compiling.
     Addition of opticsIMProtectionTypeId object to 
     OpticsIMProtectionConfigurationEntry.
     Addition of opticsIMAllowedProtectionTypesTable"

  REVISION "200802280000Z"
  DESCRIPTION 
    "Addition of opticsIMAlarmLinkOdncRaise and opticsIMAlarmLinkOdncClear,
                 opticsIMAlarmLinkCleRaise, opticsIMAlarmLinkCleClear,
                 opticsIMAlarmLinkSiRaise and opticsIMAlarmLinkSiClear.
     Addition of opticsIMIfDownstreamPortSetPorts, 
                 opticsIMIfUpstreamPortSetPorts,
		 opticsIMIfBroadcastTrafficEnable and 
		 opticsIMIfUnknownTrafficEnable to opticsIMIfEntry"

  REVISION "200711290000Z"
  DESCRIPTION
    "P.Villa:
       addition of opticsIMIfLacpEnable, opticsIMIfVplsPortRole, 
       opticsIMIfRateLimitedDcnTraffic to OpticsIMIfEntry changed to behaviour 
       of opticsIMIfRateLimitedSpeed and opticsIMIfMeanEgressShapingRate with 
       new default value (ifSpeed)
     Daniela Spreafico
       The following values has been added to opticsIMMngInterfaceType:
       - http (4)

       The following columnar object is added to OpticsIMMngInterfaceListEntry:
       - opticsIMMngInterfaceAdminState"

  REVISION "200710110000Z"
  DESCRIPTION
    "Marco Gallina
       The following values has been added to opticsIMSdhIfVcType:
       - sts-3c (8)
       - sts-12c (9)
       - sts-192c (10)
       - vt-2 (11)
       - vt-3 (12)
       - vt-6 (13)
       - pdh-e1 (14)
       - pdh-ds1 (15)
       - pdh-e3 (16)
       - pdh-ds3 (17)
     Daniela Spreafico:
       the following alarms have been added:
       - opticsimAlarmSynchronizationSignalFailRaise
       - opticsimAlarmSynchronizationSignalFailClear
       - opticsimAlarmLicenseMismatchRaise
       - opticsimAlarmLicenseMismatchClear"

  REVISION "200709180000Z"
  DESCRIPTION
    "Chen Qiao
       The OpticsIMIfDemarcRole object has been added to opticsIMIfTable"

  REVISION "200702280000Z"
  DESCRIPTION
    "Paolo Villa
       The following alarms have been added:
       - opticsimAlarmTrafficDisableRaise
       - opticsimAlarmTrafficDisableClear
       - opticsimAlarmEthOAMLossOfContinuityRaise
       - opticsimAlarmEthOAMLossOfContinuityClear
       - opticsimAlarmEthOAMMisMergeConditionRaise
       - opticsimAlarmEthOAMMisMergeConditionClear
       - opticsimAlarmEthOAMUnexpectedMepIdRaise
       - opticsimAlarmEthOAMUnexpectedMepIdClear
       - opticsimAlarmEthOAMUnexpectedPeriodRaise
       - opticsimAlarmEthOAMUnexpectedPeriodClear
       - opticsimAlarmEthOAMUnexpectedLevelRaise
       - opticsimAlarmEthOAMUnexpectedlevelClear
       - opticsimAlarmEthOAMRDIRaise
       - opticsimAlarmEthOAMRDIClear"

  REVISION "200612210000Z"
  DESCRIPTION
    "Paolo Villa
       Added OpticsIMHashingKeyList, opticsIMIfHashInput and opticsIMNeSLAType
     Zhiyong Xu:
       The following alarms have been added:
       - opticsimAlarmServerSignalIngrFailRaise
       - opticsimAlarmServerSignalIngrFailClear
       - opticsimAlarmServerSignalEgreFailRaise
       - opticsimAlarmServerSignalEgreFailClear"

  REVISION "200610190000Z"
  DESCRIPTION
    "Daniela Spreafico:
     1. the following alarms have been added:
        - opticsimAlarmMisconnectionRaise
        - opticsimAlarmMisconnectionClear
        - opticsimAlarmLateFramesRaise
        - opticsimAlarmLateFramesClear
        - opticsimAlarmMalformedFramesRaise
        - opticsimAlarmMalformedFramesClear
        - opticsimAlarmJitterBufferOverrunRaise
        - opticsimAlarmJitterBufferOverrunClear
     2. the following table has been added:
        - opticsIMProtectionConfigurationTable    
     Paolo Villa:
       the behaviour of the opticsIMIfAdmittedFloodingRate attribute, allows a 
       maximum value up to ifSpeed (defined as Gauge32).
       It has been requested to be realigned (for consistency reasons with 
       ifSpeed SNMP type) to Gauge32 SNMP type, fixing current incorrect SNMP 
       type (equal to Integer32)."

  REVISION "200608300000Z"
  DESCRIPTION
    "Paolo Villa:
       Added opticsIMifEntryPortTrafficEnabled and 
       opticsIMIfAdmittedFloodingRate to opticsIMIfTable"

  REVISION "200602280000Z"
  DESCRIPTION
    "Zhiyong Xu:
       The following alarms have been added:
       - opticsimAlarmInputPowerDegradeRaise
       - opticsimAlarmInputPowerDegradeClear"

  REVISION "200602160000Z"
  DESCRIPTION
    "Paolo Villa:
       Changed behavior of opticsIMPoolTable.
     Stefano Volonte':
       The older file as been split in four concatenated files:
       - TSDIMSpSnmpNeMibBasic: which contains MIB heading
       - TSDIMSpSnmpNeMibEMlim: which contains the part specific to EML-IM.
         When this file changes, the EML-IM has to be regenerate.
       - TSDIMSpSnmpNeMibGeneric: which contains Generic part of this file
         (mainly Notification alarms)
       - TSDIMSpSnmpNeMibMc: which contains MODULE COMPLIANCE part."
  REVISION "200510270000Z"
  DESCRIPTION
    "The following objects have been added:
     - opticsIMIfQueueTable, opticsIMIfEgressFCMappingTable
     - opticsIMAllowedNePeripheralTable, opticsIMTrsDirectionTable
     - opticsIMNeDirectionPeripheralTable, opticsIMNeCompositionTable

     Added to opticsIMIfTable:
     - opticsIMIfMeanEgressShapingRate, 
     - opticsIMIfBurstEgressShapingSize
     - opticsIMIfSchedulingDiscipline.
     Added new values to opticsIMSdhIfVcType"

  REVISION "200506160000Z"
  DESCRIPTION
    "The following objects have been added:
     - opticsimNeMtu
     - opticsIMNeMACCollectionStatus, opticsIMNeMACActivateCollection
       (included within the defined GROUP opticsIMNeMACCollection)
     - opticsIMIfRateLimitedSpeed to opticsIMIfTable
     - opticsIMPoolTable
       The behavior of the following objects have been updated:
     - opticsimIsaAccess
     The following alarms have been added:
     - opticsimAlarmDegradeRaise
     - opticsimAlarmDegradeClear

     The following objects have been added:
     - opticsIMNePMCollection, opticsIMNePMCollectionStatus,
       opticsIMNePMActivateCollection (also included within the defined GROUP 
       opticsIMNePMCollectionGroup
     - opticsimNeAutoProvisioning
     - opticsimSwPackageProfile (added also to tsdimSnmpNEGroup)
     - opticsimSwPackageProfileRequested
     - opticsimMaskNamingRules (added also to tsdimSnmpNEGroup)
     - opticsIMdatabaseModify
     - opticsIMMibConfigurationMode
     - opticsIMMngInterfaceListTable.

     The following alarms have been added to opticsimCommonAlarms and to Group 
     opticsIMOptAlarmGroup
     - opticsIMAlarmExstensionHeaderMismatchRaise
     - opticsIMAlarmExstensionHeaderMismatchClear
     - opticsIMAlarmUserPayloadMismatchRaise
     - opticsIMAlarmUserPayloadMismatchClear
     The opticsIMIfBridgeBasePort object has been added to opticsIMIfTable"

  REVISION "200406150000Z"
  DESCRIPTION
    "The following objects have been added:
     - opticsimIsaAccess
     The behavior description of the opticsimEpsConfStatus object has been
     clarified to cover the case of ISA boards with plug-able access cards
     (e.g. ISA ES-16)."

  REVISION "200404300000Z"
  DESCRIPTION
    "The following alarms have been added:
     - opticsIMAlarmLossOfPointerRaise
     - opticsIMAlarmLossOfPointerClear
     - opticsIMAlarmLossOfMultiframeRaise
     - opticsIMAlarmLossOfMultiframeClear
     - opticsIMAlarmSequenceMismatchRaise
     - opticsIMAlarmSequenceMismatchClear
     - opticsIMAlarmServerSignalFailRaise
     - opticsIMAlarmServerSignalFailClear
     - opticsIMAlarmUnequippedRaise
     - opticsIMAlarmUnequippedClear,
     The following object has been added:
     - opticsIMEquipmentName"

    REVISION "200401230000Z"
    DESCRIPTION
      "Added Alarms for WTD purposes. These larms are related to Packet 
       Concatenation and Client Signal Failure"
    REVISION "200310100000Z"
    DESCRIPTION
      "Added to tsdimIfUnderlieLayer syntax:
       - vconc(6) value
       Added to opticsIMSdhIfUnderlieLayer syntax:
       - vconc(6) value
       Added to opticsIMSdhIfTable:
       - opticsIMSdhIfCurrSpeed object
       The following alarms have been added:
       - opticsimSdhConcDegradeRaise
       - opticsimSdhConcDegradeClear
       opticsIMOffNormalDescription object has been added to abnormal 
       condition table. "

    REVISION "200307070000Z"
    DESCRIPTION
      "Added to tsdimIfUnderlieLayer syntax:
       - pconc(5) value
       Added to opticsIMSdhIfUnderlieLayer syntax:
       - mau(4) value
       - pconc(5) value
       Added to opticsIMSdhIfTable:
       - opticsIMSdhIfType object
       - opticsIMSdhIfVcType object
       The following objects have been added:
       - opticsimEpsConfStatus
       - opticsimEpsActiveRole
       The following alarms have been added:
       - opticsimGfpAlarmGtmRaise
       - opticsimGfpAlarmGtmClear
       - opticsimDAAlarmDACMRaise
       - opticsimDAAlarmDACMClear
       - opticsimlossOfAlignmentRaise
       - opticsimlossOfAlignmentClear
       - opticsimRemoteNEFailureRaise
       - opticsimRemoteNEFailureClear
       - opticsimPPPFailRaise
       - opticsimPPPClear
       The changes in the opticsIMSdhIfTable are notified
       via an AVC rather than via an SCN."

  REVISION "200303140000Z"
  DESCRIPTION
    "URU and LAPD fail alarms traps have been added."

  REVISION "200302060000Z"
  DESCRIPTION
    "Technology independent TSF and PLM alarms have been added.
     For backward-compatibility, the old TSF and PLM alarms apply to ATM 
     interfaces only."

  REVISION "200211050000Z"
  DESCRIPTION
    "New objects related to the time management have been added.
     Furthermore technology independent alarms have been added."

  REVISION "200207240000Z"
  DESCRIPTION
    "Modified access status to NE address objects."

  REVISION "200205100000Z"
  DESCRIPTION
    "New objects: NE Configuration Type Id and Market "

  REVISION "200205100000Z"
  DESCRIPTION
    "New object: NE Configuration Type "

  REVISION "200104130000Z"
  DESCRIPTION
    "Bug Fixing: info model MC modification"

  REVISION "200012200000Z"
  DESCRIPTION
    "Added the mau underlie layer."

  REVISION "200009290000Z"
  DESCRIPTION
    "Generic objects, such as opticsIMSdhIfTable, tsdimIf..., Tsf and Plm 
    alarms, have been added to this MIB and deleted from TSDIM-TRS-MIB."

  REVISION "200007010000Z"
  DESCRIPTION
    "They have been deleted the Manager address table"

  REVISION "200005090000Z"
  DESCRIPTION
    "They have been moved the IP routing and Manager Polling functionalities"

  REVISION "200002290000Z"
  DESCRIPTION
    "They have been added the following functionalities:
     - IP routing,
     - Support managemeng and
     - Polling management.
     Moreover it has been re-arranged the object description clauses and the 
     registration numbers in order to have an aggregation of objects based on 
     functionalities

     NOTA BENE:
       Reminder that each date will be defined as UTC time, hence the
       DateAndTime textual convention will be defined as:
       <actual time>+00. 
       The fixed part +00 means no timezone shifting."
  REVISION "9910210000Z"
  DESCRIPTION
    "Initial Release TSD-IM SNMP NE MIB"
::= { tsdimBasicMib 5 }

tsdimSnmpNEMibObject    OBJECT IDENTIFIER ::= { tsdimSnmpNEMib 1 }
opticsIMNeConfiguration OBJECT IDENTIFIER ::= { tsdimSnmpNEMibObject 28 }
opticsIMNTPManagement   OBJECT IDENTIFIER ::= { tsdimSnmpNEMibObject 30 }
opticsIMCommonAlarms    OBJECT IDENTIFIER ::= { tsdimSnmpNEMibObject 40}

-- TEXTUAL CONVENTION
OpticsIMMibConfigurationMode ::= TEXTUAL-CONVENTION
  STATUS current
  DESCRIPTION
    "The value of this object identifies the mode of the MIB Configuration."
  SYNTAX INTEGER {
    offline (0),
    online  (1)
}

OpticsIMMngInterfaceType ::= TEXTUAL-CONVENTION
  STATUS current
  DESCRIPTION
    "The value of this object identifies the Type of the management interface."
  SYNTAX INTEGER {
    q3    (0),
    snmp  (1),
    tl1   (2),
    cli   (3),
    http  (4)
}

OpticsIMMngInterfaceCharacterization ::= TEXTUAL-CONVENTION
  STATUS current
  DESCRIPTION
    "The value of this object identifies the Characterization of the management 
     interface."
  SYNTAX INTEGER {
    primary   (0),
    secondary (1)
}

OpticsIMMngInterfaceAddressType ::= TEXTUAL-CONVENTION
  STATUS current
  DESCRIPTION
    "The value of this object identifies the Address Type of the management 
     interface."
  SYNTAX INTEGER {
    ipAddress   (0),
    presentationAddress  (1)
}

OpticsIMHashingKeyList ::= TEXTUAL-CONVENTION
  STATUS current
  DESCRIPTION
    "Each Hashing key parameter as input to Link Aggregation Hash function is
     represented by a single bit within the  value of this object. 
     Only the first 13 bits are defined (from 0 to 12); the remaining bits 
     (from 13 to 31) have not been defined yet.
      
     Following the list of the actual hashing key parameters:
      1) bit  0: MAC Destination Address (48 bits)
      2) bit  1: MAC Source Address (48 bits)
      3) bit  2: C-VID (12 bits)
      4) bit  3: C-PRI (3 bits)
      5) bit  4: S-VID (12 bits)
      6) bit  5: S-PRI (3 bits)
      7) bit  6: All MPLS Labels (N labels*20 bits)
      8) bit  7: lowest MPLS Label (MPLS label with 1 Bottom of Stack bit)
      9) bit  8: IP Destination Address (32 bits)
     10) bit  9: IP Source Address (32 bits)
     11) bit 10: Destination Port Number (16 Bits)
     12) bit 11: Source Port Number (16 Bits)
     13) bit 12: IP DSCP (6 bits) 
     14) bit 13: I-SID (24 bits)
     15) bit 14: I-PCP (3 bits)
     16) bit 15: Ethertype (32 bit)"
  SYNTAX BITS
  {
    macDestAddr(0),
    macSourceAddr(1),
    cvid(2),
    cpri(3),
    svid(4),
    spri(5),
    alllabels(6),
    bottomlabel(7),
    ipDestAddr(8),
    ipSourceAddr(9),
    ipDestPortNumber(10),
    ipSourcePortNumber(11),
    ipDscp(12),
    isid(13),
    ipcp(14),
    etype(15)
  }

-- This is duplicated from Q-BRIDGE-MIB for permitting the 
-- IDL compiling

PortList ::= TEXTUAL-CONVENTION
  STATUS      current
  DESCRIPTION
    "Each octet within this value specifies a set of eight ports, with the 
     first octet specifying ports 1 through 8, the second octet specifying 
     ports 9 through 16, etc.
     Within each octet, the most significant bit represents the lowest numbered 
     port, and the least significant bit represents the highest numbered port.
     Thus, each port of the bridge is represented by a single bit within the
     value of this object. If that bit has a value of '1' then that port is 
     included in the set of ports; the port is not included if its bit has a 
     value of '0'."
  SYNTAX      OCTET STRING

-- End of Q-BRIDGE-MIB duplication

OpticsIMNeAlarmsNeIndex ::= TEXTUAL-CONVENTION
  STATUS current
  DESCRIPTION
    "A value used to index the NE alarms ASAP object table"
  SYNTAX Unsigned32 (1..4294967295)

-- Begin - TSDnm96257: G.Gallina 

OpticsIMcapabilityProfileIndex ::= TEXTUAL-CONVENTION
  STATUS current
  DESCRIPTION
    "Capability profile index. NE unique index."
  SYNTAX Unsigned32 (1..2147483647)

OpticsIMCapabilityIndex ::= TEXTUAL-CONVENTION
  STATUS current
  DESCRIPTION
    "Capability index. Each capability has a unique index defined by reference comumentation."
  SYNTAX Unsigned32 (1..2147483647)


-- tsdimSnmpAgtIpAddress
tsdimSnmpAgtIpAddress OBJECT-TYPE
  SYNTAX IpAddress
  MAX-ACCESS read-write
  STATUS current
  DESCRIPTION
    "This scalar object defines the Agent Ip Address"
::= { tsdimSnmpNEMibObject 1 }

-- tsdimSnmpAgtUdpPort
tsdimSnmpAgtUdpPort OBJECT-TYPE
  SYNTAX TsdimUdpPort
  MAX-ACCESS read-write
  STATUS current
  DESCRIPTION 
    "This scalar object defines the Agent UDP Port."
::= { tsdimSnmpNEMibObject 2 }

-- tsdimSnmpAgtIpMask
tsdimSnmpAgtIpMask OBJECT-TYPE
  SYNTAX IpAddress
  MAX-ACCESS read-write
  STATUS current
  DESCRIPTION
    "This scalar object defines the Agent Ip Mask"
::= { tsdimSnmpNEMibObject 3 }

-- tsdimSnmpAgtIPv6Address
tsdimSnmpAgtIPv6Address OBJECT-TYPE
  SYNTAX InetAddressIPv6
  MAX-ACCESS read-write
  STATUS current
  DESCRIPTION
    "This scalar object defines the Agent Ip Address in IPv6 format"
::= { tsdimSnmpNEMibObject 61 }

-- tsdimNeInstallationType
tsdimNeInstallationType OBJECT-TYPE
  SYNTAX DisplayString
  MAX-ACCESS read-only
  STATUS current
  DESCRIPTION
    "This scalar object defines the NE Installation type."
::= { tsdimSnmpNEMibObject 5 }

-- tsdimSdhNeLabel
tsdimSdhNeLabel OBJECT-TYPE
  SYNTAX DisplayString
  MAX-ACCESS read-write
  STATUS current
  DESCRIPTION
    "This object defines the  SDH NE user label"
::= { tsdimSnmpNEMibObject 13 }

-- tsdimBoardPosition
tsdimBoardPosition OBJECT-TYPE
  SYNTAX Integer32
  MAX-ACCESS read-only
  STATUS current
  DESCRIPTION 
    "This object defines the  board position in term of <rrssbb>"
::= { tsdimSnmpNEMibObject 14 }

-- tsdimLacTable
tsdimLacTable OBJECT-TYPE
  SYNTAX SEQUENCE OF TsdimLacEntry
  MAX-ACCESS not-accessible
  STATUS current
  DESCRIPTION
    "The TSDIM Local Access control table.
     This table is used to give access to the Craft Terminals."
::= { tsdimSnmpNEMibObject 17 }

tsdimLacEntry OBJECT-TYPE
  SYNTAX TsdimLacEntry
  MAX-ACCESS not-accessible
  STATUS current
  DESCRIPTION
    "Entry is automatically created by Agent at start-up time."
  INDEX { tsdimLacIndex }
::= { tsdimLacTable 1 }

TsdimLacEntry ::= SEQUENCE {
  tsdimLacState INTEGER,
  tsdimLacNoResponseTimeOutPeriod Integer32,
  tsdimLacIndex Integer32
}

tsdimLacState OBJECT-TYPE
  SYNTAX INTEGER {
    accessDenied (0),
    accessRequested (1), 
    accessGranted (2) }
  MAX-ACCESS read-write
  STATUS current
  DESCRIPTION
    "This is the State attribute for the Local Access Control.
     This attribute can be set:
     - by Agent at creation time to accessRequested 
     - by EML to the values accessGranted or accessDenied"
::= { tsdimLacEntry 1 }

tsdimLacNoResponseTimeOutPeriod OBJECT-TYPE
  SYNTAX Integer32 (0..3600)
  UNITS "seconds"
  MAX-ACCESS read-write
  STATUS current
  DESCRIPTION
    "This is the No Response TimeOut Period attribute for the Local Access \
     Control."
::= { tsdimLacEntry 2 }

tsdimLacIndex OBJECT-TYPE
  SYNTAX Integer32
  MAX-ACCESS not-accessible
  STATUS current
  DESCRIPTION
    "This is the index for the Local Access Control table."
::= { tsdimLacEntry 3 }

-- opticsIMNeOwnsByMgr
opticsIMNeOwnsByMgr OBJECT-TYPE
  SYNTAX DisplayString
  MAX-ACCESS read-write
  STATUS current
  DESCRIPTION
    "This scalar object contains the label which identify the manager that is 
     managing the NE"
::= { tsdimSnmpNEMibObject 18 }

-- tsdimInfoModelVersionMajor
tsdimInfoModelVersionMajor OBJECT-TYPE
  SYNTAX Integer32
  MAX-ACCESS read-only
  STATUS current
  DESCRIPTION
    "This is the infomodel major version value."
::= { tsdimSnmpNEMibObject 25 }

-- tsdimInfoModelVersionMinor
tsdimInfoModelVersionMinor OBJECT-TYPE
  SYNTAX Integer32
  MAX-ACCESS read-only
  STATUS current
  DESCRIPTION 
    "This is the infomodel minor version value"
::= { tsdimSnmpNEMibObject 26 }

-- tsdimInfoModelVersionMaintenance
tsdimInfoModelVersionMaintenance OBJECT-TYPE
  SYNTAX DisplayString
  MAX-ACCESS read-only
  STATUS current
  DESCRIPTION
    "This is the infomodel maintenance version value"
::= { tsdimSnmpNEMibObject 27 }

-- opticsimMaskNamingRule
opticsimMaskNamingRule OBJECT-TYPE
  SYNTAX DisplayString
  MAX-ACCESS read-only
  STATUS current
  DESCRIPTION
    "The value of this object provides the mask of the naming of the TTPs.
     The mask indicates the binary format of the naming composed by the 
     following fields:
       x for data purposes field, 
       r for rack field, 
       s for subrack field, 
       b for board field, 
       d for drawer field, 
       p for port field,
       c for channel field.
     The mask allows the decoding of the naming, specifying for each field 
     (all the fields are present and in the above listed order) the number of 
     reserved bits followed by the character (above provided) that identifies 
     the field itself.
     In case a field is never used inside the NE, the field is anyway present 
     with number of reserved bits 0 (e.g. if the drawer is never used an 
     example of mask is 4x3r3s10b0d10p2c)."
::= { tsdimSnmpNEMibObject 34 }

-- Start opticsIMMngInterfaceListTable
opticsIMMngInterfaceListTable OBJECT-TYPE
  SYNTAX SEQUENCE OF OpticsIMMngInterfaceListEntry
  MAX-ACCESS not-accessible
  STATUS current
  DESCRIPTION
    "This table defines the list of management Interfaces with: management 
     interface type, address and its charaterization.
     The address allows reaching the NE applications (Agents) in charge of the 
     specific management interface.
     In case of SNMP Agent, where for the address an ASN.1 Octect String is 
     simply defined, this string, aligned to SNMPv2-SMI, has to be composed as 
     follows: IpAddress:PortNumber.

     In case of Q3 Agent,  a presentation address consists of octect strings 
     with:
       - presentation selector, session selector, transport selector and a set 
         of network addresses as defined in RFC 1278.

     The characterization defines the primary and secondary management 
     interfaces.

     Primary is the management interface where basic functionalities, like 
     Equipment, LAC, NTP, File Transfer, etc. are accessible."
::= { tsdimSnmpNEMibObject 39 }

opticsIMMngInterfaceListEntry OBJECT-TYPE
  SYNTAX OpticsIMMngInterfaceListEntry
  MAX-ACCESS not-accessible
  STATUS current
  DESCRIPTION
    "see description of opticsIMMngInterfaceListTable "
  INDEX { opticsIMMngInterfaceListIndex }
::= { opticsIMMngInterfaceListTable 1 }

OpticsIMMngInterfaceListEntry ::= SEQUENCE {
  opticsIMMngInterfaceListIndex INTEGER,
  opticsIMMngInterfaceType OpticsIMMngInterfaceType,
  opticsIMMngInterfaceCharacterization OpticsIMMngInterfaceCharacterization,
  opticsIMMngInterfaceAddressType OpticsIMMngInterfaceAddressType,
  opticsIMMngInterfaceAddress DisplayString,
  opticsIMMngInterfaceAdminState INTEGER
}

opticsIMMngInterfaceListIndex OBJECT-TYPE
  SYNTAX INTEGER
  MAX-ACCESS not-accessible
  STATUS current
  DESCRIPTION
    "Index of opticsIMMngInterfaceListEntry "
::= { opticsIMMngInterfaceListEntry 1 }

opticsIMMngInterfaceType OBJECT-TYPE
  SYNTAX OpticsIMMngInterfaceType
  MAX-ACCESS read-only
  STATUS current
  DESCRIPTION
    "It defines the type of the management interface."
::= { opticsIMMngInterfaceListEntry 2 }

opticsIMMngInterfaceCharacterization OBJECT-TYPE
  SYNTAX OpticsIMMngInterfaceCharacterization
  MAX-ACCESS read-only
  STATUS current
  DESCRIPTION
    "The characterization defines the primary and secondary management 
     interfaces.
     Primary is the management interface where basic functionalities, like 
     Equipment, LAC, NTP, File Transfer, etc. are accessible."
::= { opticsIMMngInterfaceListEntry 3 }

opticsIMMngInterfaceAddressType OBJECT-TYPE
  SYNTAX OpticsIMMngInterfaceAddressType
  MAX-ACCESS read-only
  STATUS current
  DESCRIPTION
    "It defines the address type of the management interface."
::= { opticsIMMngInterfaceListEntry 4 }

opticsIMMngInterfaceAddress OBJECT-TYPE
  SYNTAX DisplayString
  MAX-ACCESS read-only
  STATUS current
  DESCRIPTION
    "It defines the address associated to the management interface.
     In case of Ip Address DisplayString is encoded aligned to SNMPv2-SMI, in 
     case of Presentation Address  DisplayString is encoded aligned to 
     RFC 1278."
::= { opticsIMMngInterfaceListEntry 5 }

opticsIMMngInterfaceAdminState OBJECT-TYPE
  SYNTAX  INTEGER {
    enable(1),
    disable(2)
  }
  MAX-ACCESS read-write
  STATUS current
  DESCRIPTION
    "It defines the administrative state of the management interface.
     When this object is set to 'disable' value then the NE is not allowed to 
     be supervised from this management interface."
::= { opticsIMMngInterfaceListEntry 6 }

-- End opticsIMMngInterfaceListTable

-- opticsIMExternalTime
opticsIMExternalTime OBJECT-TYPE
  SYNTAX  DateAndTime
  MAX-ACCESS read-write
  STATUS current
  DESCRIPTION
    "This object specifies the current time of the NE. This time has to be used
     as reference for all time stamp activities in the NE."
::= { tsdimSnmpNEMibObject 29 }

-- opticsIMNTPStatus
opticsIMNTPStatus OBJECT-TYPE
  SYNTAX INTEGER { 
    enabled (1),
    disabled (2) }
  MAX-ACCESS read-write
  STATUS current
  DESCRIPTION
    "This object is used to enable/disable the Network Time Protocol (NTP)."
::= { opticsIMNTPManagement 1 }

-- opticsIMMainNTPServerAddress
opticsIMMainNTPServerAddress OBJECT-TYPE
  SYNTAX IpAddress
  MAX-ACCESS read-write
  STATUS current
  DESCRIPTION
    "This object contains the address of the main server of the Network Time 
     Protocol (NTP)."
::= { opticsIMNTPManagement 2 }

-- opticsIMSpareNTPServerAddress
opticsIMSpareNTPServerAddress OBJECT-TYPE
  SYNTAX IpAddress
  MAX-ACCESS read-write
  STATUS current
  DESCRIPTION
    "This object contains the address of the spare server of the Network Time 
     Protocol (NTP)."
::= { opticsIMNTPManagement 3 }

-- opticsIMNTPServersReachabilityStatus
opticsIMNTPServersReachabilityStatus OBJECT-TYPE
  SYNTAX INTEGER {
    noServerReachable (1), 
    onlyMainServerReachable (2),
    onlySpareServerReachable (3),
    mainAndSpareServersReachable (4) }
  MAX-ACCESS read-only
  STATUS current
  DESCRIPTION
    "This object is used to indicate if the Network Time Protocol (NTP) servers 
     (main and spare) are reachable."
::= { opticsIMNTPManagement 4 }

-- opticsIMMainNTPServerIPv6Address
opticsIMMainNTPServerIPv6Address OBJECT-TYPE
  SYNTAX InetAddressIPv6
  MAX-ACCESS read-write
  STATUS current
  DESCRIPTION
    "This object contains the address of the main server of the Network Time 
     Protocol (NTP) in the IPv6 format."
::= { opticsIMNTPManagement 62 }

-- opticsIMSpareNTPServerIPv6Address
opticsIMSpareNTPServerIPv6Address OBJECT-TYPE
  SYNTAX InetAddressIPv6
  MAX-ACCESS read-write
  STATUS current
  DESCRIPTION
    "This object contains the address of the spare server of the Network Time 
     Protocol (NTP) in the IPv6 format."
::= { opticsIMNTPManagement 63 }
-- Note:
-- The END string below has to be "uncommented" when only the EMLIM part of the 
-- TSDIMSpSnmpNeMib have to be compiled.
--
-- Then the file has to be composed as: 
--     TSDIMSpSnmpNeBasicxxx.mib + TSDIMSpSnmpNeEmlimxxx.mib = TSDIMSpSnmpNeMibMcxxx.mib 
--

-- END 

-- opticsIMIfTable
opticsIMIfTable OBJECT-TYPE
  SYNTAX SEQUENCE OF OpticsIMIfEntry
  MAX-ACCESS not-accessible
  STATUS current
  DESCRIPTION 
    "This table contains interface configuration not defined in the IfTable 
     (see inside the IF-MIB)."
::= { tsdimSnmpNEMibObject 19 }

opticsIMIfEntry OBJECT-TYPE
  SYNTAX OpticsIMIfEntry
  MAX-ACCESS not-accessible
  STATUS current
  DESCRIPTION
    "An entry extends IfTable."
  INDEX { ifIndex }
::= { opticsIMIfTable 1 }

OpticsIMIfEntry ::= SEQUENCE {
  tsdimIfUnderlieLayer              INTEGER,
  tsdimIfAsapIndex                  Integer32,
  tsdimIfOwnsByMgr                  TsdimManagerType,
  opticsIMIfTxSL                    SLValue,
  opticsIMIfExpSL                   SLValue,
  opticsIMIfRxSL                    SLValue,
  opticsIMIfSLSendControl           INTEGER,
  opticsIMIfBridgeBasePort          Integer32,
  opticsIMIfRateLimitedSpeed        Gauge32,
  opticsIMIfMeanEgressShapingRate   Gauge32,
  opticsIMIfBurstEgressShapingSize  Unsigned32,
  opticsIMIfSchedulingDiscipline    INTEGER,
  opticsIMIfEntryPortTrafficEnabled INTEGER,
  opticsIMIfAdmittedFloodingRate    Gauge32,
  opticsIMIfHashInput               OpticsIMHashingKeyList,
  opticsIMIfDemarcRole              INTEGER,
  opticsIMIfLacpEnable              TruthValue, 
  opticsIMIfVplsPortRole            INTEGER,
  opticsIMIfRateLimitedDcnTraffic   Gauge32,
  opticsIMIfDownstreamPortSetPorts  PortList,
  opticsIMIfUpstreamPortSetPorts    PortList,
  opticsIMIfBroadcastTrafficEnable  TruthValue,
  opticsIMIfUnknownTrafficEnable    TruthValue,
  opticsIMIfPdhRate                 INTEGER,
  opticsIMIfOffsetEgressShapingSize Unsigned32,
  opticsIMIfPIPMacAddress           PhysAddress,
  opticsIMIfMCEnable                TruthValue,
  opticsIMIfLPTSendControl          INTEGER, 
  opticsIMIfLPTCsfConsequentActions INTEGER,
  opticsIMIfLPTSsfConsequentActions INTEGER,
  opticsIMIfLPTHoldOffTime          INTEGER,
  opticsIMIfBroadcastTrafficLimit       Gauge32, 
  opticsIMIfMulticastTrafficLimit       Gauge32, 
  opticsIMIfUnknownUnicastTrafficLimit  Gauge32,
  opticsIMIfAvailableBandwidth      Integer32,
  opticsIMIfNetBandwidth      	    Integer32,
  opticsIMIfUnknownMulticastTrafficLimit  Gauge32,
  
--- BEGIN per-port capability
  opticsIMPortCapabilityIndex       Integer32,
 --- END per-port capability
-- Begin OPTnm02313 
  opticsIMIfSwitchId		        INTEGER,
-- End OPTnm02313

  opticsIMIfUserLabel	 	    OpticsIMUserLabel,

  opticsIMIfPortAlarmAdmin              INTEGER,
  
-- Begin OPTnm20039 April 2013 for L3VPN
  opticsIMIfIpIntfPointer         Unsigned32,                  	       
-- End OPTnm20039 April 2013
-- Begin OPTnm23953 July 2013
  opticsIMIfAlarmReeval           TruthValue,
-- End OPTnm23953 July 2013
-- Begin OPTnm26463 
  opticsIMIflnkaggThreshold		INTEGER,
-- End OPTnm26463 
-- Begin SNMPIDL-494 
  opticsIMIf1588TCStatus		INTEGER
-- End SNMPIDL-494 
}

tsdimIfUnderlieLayer OBJECT-TYPE
  SYNTAX INTEGER {
    sdh (1),
    pdh (2),
    none (3),
    mau (4),
    pconc (5),
    vconc (6)  }
  MAX-ACCESS read-write
  STATUS current
  DESCRIPTION
    "This object contains the reference to the underlying path layer
     termination point.
     This object can be set only when used as physical interface.
     The default value is <none>."
::= { opticsIMIfEntry 1 }

tsdimIfAsapIndex OBJECT-TYPE
  SYNTAX Integer32 (1..2147483647)
  MAX-ACCESS read-write
  STATUS current
  DESCRIPTION
    "This object defines the ASAP object associated to this interface."
::= { opticsIMIfEntry 2 }

tsdimIfOwnsByMgr OBJECT-TYPE
  SYNTAX TsdimManagerType
  MAX-ACCESS read-write
  STATUS current
  DESCRIPTION
    "This attribute defines the manager which is the owner of the resources 
     involved in this connection"
::=  { opticsIMIfEntry 3 }

opticsIMIfTxSL OBJECT-TYPE
  SYNTAX SLValue
  MAX-ACCESS read-only
  STATUS current
  DESCRIPTION
    "This attribute defines the SL value transmitted in the outgoing direction."
::= { opticsIMIfEntry 4 }

opticsIMIfExpSL OBJECT-TYPE
  SYNTAX SLValue
  MAX-ACCESS read-only
  STATUS current
  DESCRIPTION
    "This attribute defines the SL value expected in the incoming direction."
::= { opticsIMIfEntry 5 }

opticsIMIfRxSL OBJECT-TYPE
  SYNTAX SLValue
  MAX-ACCESS read-only
  STATUS current
  DESCRIPTION
    "This attribute defines the SL value received in the incoming direction."
::= { opticsIMIfEntry 6 }

opticsIMIfSLSendControl OBJECT-TYPE
  SYNTAX INTEGER {
    automatic(0),
    forced(1)}
  MAX-ACCESS read-write
  STATUS current
  DESCRIPTION
    "This attribute defines if the transmitted SL value shall be defined by 
     the agent according to the payload type or it should be the 
     'equipped-non-specific' code.

     The value 'automatic' (0) means that the tx SL is calculated by the agent 
     according to the payload type.

     The value 'forced' (1) means that the tx SL has been forced by the 
     manager to the 'equipped-non-specific' code.

     This object can be set when the AdminStatus is down or up."
::= { opticsIMIfEntry 7 }

opticsIMIfBridgeBasePort OBJECT-TYPE
  SYNTAX      Integer32 (0..65535)
  MAX-ACCESS  read-only
  STATUS      current
  DESCRIPTION
    "This attribute value is the  bridge port number which lets manager get 
     bridge tables indexed by this number.

     The default value is equal to zero when no bridge port is created and 
     associated by SNMP agent.

     When a bridge port can be equipped (its related Ethernet interface is Up, 
     with promiscuous mode and with ETB characterization in case of IEEE 8021.d,
     8021.q or also with ETS characterization in case of IEEE 8021.ad), SNMP
     agent assigns its chosen index to this attribute"
::= { opticsIMIfEntry 8 }

opticsIMIfRateLimitedSpeed OBJECT-TYPE
  SYNTAX      Gauge32
  MAX-ACCESS  read-write
  STATUS      current
  DESCRIPTION
    "This attribute carries out the rate limiting functionality.
     ifSpeed value means that the rate limitation of the interface is disabled;
     this is the default value.

     The value 0 means that the rate limitation of the interface is disabled; 
     this is the default value. 
     The value can be expressed in bit/s or kbit/s NE dependent"
::= { opticsIMIfEntry 9 }

opticsIMIfMeanEgressShapingRate OBJECT-TYPE
  SYNTAX      Gauge32
  MAX-ACCESS  read-write
  STATUS      current
  DESCRIPTION
    "This attribute carries out the egress shaping rate (sustained rate 
     permitted by egress traffic shaping) in kbit/sec. Disabled rate limitation 
     is the default value."

--     ifSpeed value means that the rate limitation of the interface is disabled; 
--     this is the default value.
--    The value 0 means that the egress shaping rate limitation 
--    of the interface is disabled; this is the default value.
::= { opticsIMIfEntry 10 }

opticsIMIfBurstEgressShapingSize OBJECT-TYPE
  SYNTAX      Unsigned32
  MAX-ACCESS  read-write
  STATUS      current
  DESCRIPTION
    "This attribute carries out the burst egress shaping size (amount of 
     traffic in excess of egress shaping rate) in bytes.
     Default value 0 (null burst egress shaping size)"
::= { opticsIMIfEntry 11 }

opticsIMIfSchedulingDiscipline OBJECT-TYPE
  SYNTAX INTEGER
  MAX-ACCESS read-write
  STATUS current
  DESCRIPTION
    "This object defines 'on per port basis' scheduling disciplines according 
     to below values:
     - WorkConserving (1)
     - NonWorkConserving (2).
     Default value is WorkConserving(1)"
::= { opticsIMIfEntry 12 }

opticsIMIfEntryPortTrafficEnabled  OBJECT-TYPE
  SYNTAX INTEGER {
    up(1),
    down(2)
  }
  MAX-ACCESS  read-write
  STATUS      current
  DESCRIPTION
    "opticsIMifEntryPortTrafficEnabled specifies the current transmit/receive 
     state of the interface as a result of explicit management action applied 
     to an interface whose ifAdminStatus is up. 
     The up(1) value indicates the interface is ready to transmit and receive 
     network traffic, the down(2) value indicates the interface has blocked 
     both transmit and receive traffic capabilities.

     If ifAdminStatus is down, then opticsIMifEntryPortTrafficEnabled takes 
     down(2) value, if ifAdminStatus is changed to up(1) then 
     opticsIMifEntryPortTrafficEnabled changes to up(1)"
::= { opticsIMIfEntry  13 }

opticsIMIfAdmittedFloodingRate OBJECT-TYPE
  SYNTAX Gauge32
  MAX-ACCESS read-write
  STATUS current
  DESCRIPTION
    "This attribute carries out 'on per port basis' ingress admitted flooding 
     rate (the threshold value of admitted bandwidth for NE generated flooding 
     traffic as admitted on this ingress interface) and is specified in 
     kilobits per second (Kbps).

     This value is requested to trigger discarding of NE generatedflooding 
     traffic on this ingress interface and is minor or equal to that specified 
     in ifSpeed for this interface. Disabled flooding rate limitation 
     is the default value"

---  ifSpeed value for this attribute means that the flooding rate limitation 
---  of the interface is disabled; this is the default value.
::= { opticsIMIfEntry  14 }

opticsIMIfHashInput OBJECT-TYPE
  SYNTAX OpticsIMHashingKeyList
  MAX-ACCESS read-write
  STATUS current
  DESCRIPTION
    "This attribute enables to choose out 'on per link aggregation interface 
     basis' ingress parameters for hash function.

     If the bit is 1 it indicates that the relative hashing key parameter will 
     be used for Link Aggregation hash function otherwise if 0 it will be 
     unused.

     Default value is:
     a) for Link Aggregation Interface in promiscous mode: bit 0 (MAC DA) and 
        bit 1 (MAC SA) set to 1 and all other bits set to 0; 
     b) for Link Aggregation in non-promiscous mode: bit  6 (All MPLS Labels) 
        set to 1  and all other bits set to 0.
     This attribute is significant only for Link Aggregation interface"
::= { opticsIMIfEntry  15 }

opticsIMIfDemarcRole OBJECT-TYPE
  SYNTAX INTEGER {
    cif(1),
    nif(2),
    internal(3),
    other(4),
    internalTraffic (5), 
    internalPower (6),
    equipmentPower (7)
  }
  MAX-ACCESS read-write
  STATUS current
  DESCRIPTION
    "The Current role of the Port. Ports connected with Customer Network will 
     be called as CustomerInterface(1). Ports connected with Provider Network 
     will be called as NetworkINterface(2). The ports which are internally 
     connected to CPU and FPGA are called as Internal(3).
     The ports  which are connected to internal equipment for data traffic are called as internalTraffic (5).
     The ports  which are connected to internal equipment to provide power are called as internalPower (6).
     The ports  which are connected to external equipment to provide power are called as equipmentPower (7).
    "
::= { opticsIMIfEntry  16 }
 
--- CRB Oct 2007 Begin
opticsIMIfLacpEnable OBJECT-TYPE
  SYNTAX     TruthValue
  MAX-ACCESS read-create
  STATUS current
  DESCRIPTION
    "This parameter enables the usage of LACP protocol over Link Aggregation 
     interface.
     Default value is True (enabled LACP)"
::= { opticsIMIfEntry 17  }

opticsIMIfVplsPortRole OBJECT-TYPE
  SYNTAX INTEGER {
    vpls-uni(1),
    pvlan-spoke(2),
    pw-spoke(3),
    vpls-nni(4),
    other(5)
  }
  MAX-ACCESS read-write
  STATUS current
  DESCRIPTION
    "The Current role of a Port inside VPLS PE. 
     Ports connected with Customer Network will be called as vpls_uni(1). 
     Ports connected with MPLS Core PW will be called as vpls_nni(4). 
     Spoke ports carrying PVLAN will be called as pvlan_spoke(2). 
     Spoke ports carrying PW will be called as pw_spoke(3).
     Provider Bridge Network Port will be called as other(5)."
::= { opticsIMIfEntry  18 }

opticsIMIfRateLimitedDcnTraffic OBJECT-TYPE
  SYNTAX      Gauge32
  MAX-ACCESS  read-write
  STATUS      current
  DESCRIPTION
    "This attribute carries out the rate limiting functionality for DCN traffic
     (control Plane and Management Plane) addressed to CPU.
     A value equal to interface line-rate  means that the rate limitation of 
     DCN traffic is disabled; this is the default value.
     The value can be expressed in bit/s or kbit/s NE dependent "
::= { opticsIMIfEntry 19 } 

--- CRB Oct 2007 End 

opticsIMIfDownstreamPortSetPorts OBJECT-TYPE
  SYNTAX      PortList
  MAX-ACCESS  read-create
  STATUS      current
  DESCRIPTION
    "The set of NE ports which are permanently assigned by management to the 
     egress downstream port list (list of egress ports supporting trasmitter 
     shutdown or insertion of GFP CSF frames) in front of failure occurring on 
     this interface.

     The bit position in the egress downstream port list is coded according to 
     the dot1dBasePort parameter.

     The default value of this object is a string of zeros of appropriate 
     length, indicating not being a member (egress port without trasmitter 
     shutdown and GFP CSF failure propagation).

     This attribute is relevant ONLY in case of opticsIMEthETSServiceType equal 
     to other."
::= { opticsIMIfEntry 20 }

opticsIMIfUpstreamPortSetPorts OBJECT-TYPE
  SYNTAX      PortList
  MAX-ACCESS  read-create
  STATUS      current
  DESCRIPTION
    "The set of NE ports which are permanently assigned by management to the 
     upstream port list, where upstream port list includes those NE ports able 
     to trigger transmitted shut-down consequent action on this interface: 
     operational consequent action on this interface is constrained to combined 
     failure conditions detected (logical AND) over entire upstream port list.
     The bit position in the ingress upstream port list is coded according to 
     the dot1dBasePort parameter.

     The default value of this object is a string of zeros of appropriate 
     length, indicating not being a member (ingress port triggering no 
     consequent action).

     This attribute is relevant ONLY in case of opticsIMEthETSServiceType equal 
     to other."
::= { opticsIMIfEntry  21 }

opticsIMIfBroadcastTrafficEnable  OBJECT-TYPE
  SYNTAX      TruthValue
  MAX-ACCESS  read-write
  STATUS      current
  DESCRIPTION
    "opticsIMifBroadcastTrafficEnable specifies the broadcast traffic transmit 
     capability of an egress interface as a result of explicit management 
     action. 

     True value (Default value) indicates the interface is enabled to transmit 
     broadcast traffic, false value indicates the interface is denied to 
     transmit broadcast traffic."
    ::= { opticsIMIfEntry  22 }

opticsIMIfUnknownTrafficEnable  OBJECT-TYPE
  SYNTAX      TruthValue
  MAX-ACCESS  read-write
  STATUS      current
  DESCRIPTION
    "opticsIMifUnknownTrafficEnable specifies the unknown traffic transmit
     capability of an egress interface as a result of explicit management
     action. 

     True value (Default value) indicates the interface is enabled to transmit 
     unknown traffic, false value indicates the interface is denied to transmit 
     unknown traffic."
::= { opticsIMIfEntry  23 }

opticsIMIfPdhRate OBJECT-TYPE
  SYNTAX INTEGER {
    e1(1),
    ds1(2),
    e3(3),
    ds3(4)
  }
  MAX-ACCESS read-write
  STATUS     current
  DESCRIPTION
    "This parameter specifies the type of PDH signal carried by the interface."
::= { opticsIMIfEntry  24 }
    
opticsIMIfOffsetEgressShapingSize OBJECT-TYPE
  SYNTAX      Unsigned32
  MAX-ACCESS  read-write
  STATUS      current
  DESCRIPTION
    "This attribute carries out the server-layer offset (in bytes) for each
     specific frame. As a consequence, per-port basis egress shaping rate is
     decreased by a delta value inferred via per-frame basis server-layer
     encapsulation header. 
     Default value is indicated as 0xFFFF and is internally set according to 
     the following considerations:
     - if opticsIMNeFrameSizeMode is equal to layer2 than the default set is 
       equal to 0 (no offset).
     - if opticsIMNeFrameSizeMode is equal to layer1 than the default set is 
       interface type specific
"
::= { opticsIMIfEntry 25 }

opticsIMIfPIPMacAddress OBJECT-TYPE
  SYNTAX      PhysAddress
  MAX-ACCESS  read-write
  STATUS      current
  DESCRIPTION
    "This attribute contains user-provisioned PIP MAC address"
::= { opticsIMIfEntry 26 }
    
opticsIMIfMCEnable OBJECT-TYPE
  SYNTAX     TruthValue
  MAX-ACCESS read-create
  STATUS current
  DESCRIPTION
    "This parameter enables the interworking with Media Converter.
     Default value is False (no interworking with Media Converter)"
::= { opticsIMIfEntry 27  }


opticsIMIfLPTSendControl OBJECT-TYPE
    SYNTAX INTEGER 
    MAX-ACCESS read-write
    STATUS current
    DESCRIPTION
        "This attribute enables or disables the usage of per-port LPT transmit 
         capability. Allowed values:
         - disabled      (0)	no consequent LPT frame (IDLE insertion)   
         - gfpcsf        (1)    via opticsimGFPConfCsf
         - linkoam       (2)    802.3ah
         This object can be set when the AdminStatus is down or up."
::= { opticsIMIfEntry 28 }

opticsIMIfLPTCsfConsequentActions OBJECT-TYPE
    SYNTAX INTEGER 
    MAX-ACCESS read-write
    STATUS current
    DESCRIPTION
        "This attribute defines per-port LPT CSF Consequent Actions 
         This object identifies the consequent action triggered on 
         CIF Interface egress port for port-to-port application
         in front of received LPT Frame indications 
         (due to detected remote CIF Ethernet PHY Interface failures).

         The choice of enabled LPT CSF consequent actions is allowed to be 
         different from LPT SSF consequent actions (consequent actions 
         coping with network failures).
         Allowed values:

        - disabled (0) - default value - is defined to perform 
                          no consequent actions.
        - tx_shutdown(1) is defined to trigger forced transmitter 
                         shut-down action
        - gfp_csf     (2) is defined to trigger GFP CSF transmission
        - linkoam_cle (3) is defined to trigger Link OAM CLE transmission
           
        If the interface is not involved in a port-to-port application
        this consequent action will never be triggered.
        This object can be set when the AdminStatus is down or up."
::= { opticsIMIfEntry 29 }

opticsIMIfLPTSsfConsequentActions OBJECT-TYPE
    SYNTAX INTEGER 
    MAX-ACCESS read-write
    STATUS current
    DESCRIPTION
        "This attribute defines per-port LPT SSF Consequent Actions 
         This object identifies the consequent action triggered on 
         CIF Interface egress port for port-to-port application
         in front of Server Layer failures.

         The choice of enabled LPT SSF consequent actions is allowed to be
         different from LPT CSF consequent actions (consequent actions 
         coping with in front of LPT Frame indications).
         Allowed values:

        - disabled (0) - default value - is defined to perform 
                          no consequent actions.
        - tx_shutdown(1) is defined to trigger forced transmitter 
                         shut-down action
        - gfp_csf     (2) is defined to trigger GFP CSF transmission
        - linkoam_cle (3) is defined to trigger Link OAM CLE transmission
          
        If the interface is not involved in a port-to-port application
        this consequent action will never be triggered.
        This object can be set when the AdminStatus is down or up."
::= { opticsIMIfEntry 30 }

opticsIMIfLPTHoldOffTime OBJECT-TYPE
       SYNTAX INTEGER (0..100)
       MAX-ACCESS read-write
       STATUS current
       DESCRIPTION
          "This  attribute specifies consequent Actions Hold-Off values in 
           steps di 0.1 sec. Default Value is 0"
::= { opticsIMIfEntry 31 }
opticsIMIfBroadcastTrafficLimit OBJECT-TYPE
  SYNTAX Gauge32
  MAX-ACCESS read-write
  STATUS current
  DESCRIPTION
    "This attribute carries out 'on per port basis' ingress admitted broadcast  
     traffic rate (the threshold value of broadcast traffic rate as admitted on this ingress 
     interface) and is specified in Kilobits per second (Kbps).

     This value is requested to trigger discarding of NE generated broadcast  
     traffic on this ingress interface and is minor or equal to that specified 
     in ifSpeed for this interface.
     Disabled broadcast traffic rate limitation is the default value."
---     ifSpeed value for this attribute means that the admitted broadcast traffic rate limitation 
---     of the interface is disabled; this is the default value."
::= { opticsIMIfEntry  32 }

opticsIMIfMulticastTrafficLimit OBJECT-TYPE
  SYNTAX Gauge32
  MAX-ACCESS read-write
  STATUS current
  DESCRIPTION
    "This attribute carries out 'on per port basis' ingress admitted multicast traffic  
     rate (the threshold value of multicast traffic rate  as admitted on this ingress interface) 
     and is specified in Kilobits per second (Kbps).

     This value is requested to trigger discarding of NE generated multicast  
     traffic on this ingress interface and is minor or equal to that specified 
     in ifSpeed for this interface.
     Disabled multicast traffic rate limitation is the default value."
---    ifSpeed value for this attribute means that the admitted multicast traffic rate limitation 
---     of the interface is disabled; this is the default value.
::= { opticsIMIfEntry  33 }

opticsIMIfUnknownUnicastTrafficLimit OBJECT-TYPE
  SYNTAX Gauge32
  MAX-ACCESS read-write
  STATUS current
  DESCRIPTION
    "This attribute carries out 'on per port basis' ingress admitted unknown unicast  
     rate (the threshold value of  unknown unicast traffic rate as admitted on this ingress 
     interface) and is specified in Kilobits per second (Kbps).

     This value is requested to trigger discarding of NE generated  unknown unicast
     traffic rate on this ingress interface and is minor or equal to that specified 
     in ifSpeed for this interface.
     Disabled unknown unicast limitation is the default value."
---     ifSpeed value for this attribute means that the admitted unknown unicast limitation 
---     of the interface is disabled; this is the default value.
::= { opticsIMIfEntry  34 }

opticsIMIfAvailableBandwidth OBJECT-TYPE
  SYNTAX Integer32 (1..2147483647)
  MAX-ACCESS read-only
  STATUS current
  DESCRIPTION
    "This value indicates the total amount of available bandwidth available on 
     this interface and is specified in kilobits per second (Kbps).
     This value is calculated as the difference between the amount of bandwidth
     currently in use and that specified in ifSpeed (converted in Kbps).
     When this value cannot be measured, this value should contain the nominal 
     bandwidth."
::= { opticsIMIfEntry  35 }

opticsIMIfNetBandwidth OBJECT-TYPE
  SYNTAX Integer32 (1..2147483647)
  MAX-ACCESS read-only
  STATUS current
  DESCRIPTION
    "This value indicates the total amount of maximum bandwidth available on 
     this interface and is specified in kilobits per second (Kbps).
     "
::= { opticsIMIfEntry  36 }

opticsIMIfUnknownMulticastTrafficLimit OBJECT-TYPE
  SYNTAX Gauge32
  MAX-ACCESS read-write
  STATUS current
  DESCRIPTION
    "This attribute carries out 'on per port basis' ingress admitted unknown multicast  
     rate (the threshold value of  unknown multicast traffic rate as admitted on this ingress 
     interface) and is specified in Kilobits per second (Kbps).

     This value is requested to trigger discarding of NE generated  unknown mulitcast
     traffic rate on this ingress interface and is minor or equal to that specified 
     in ifSpeed for this interface.
     Disabled unknown multicast limitation is the default value."
---     ifSpeed value for this attribute means that the admitted unknown multicast limitation 
---     of the interface is disabled; this is the default value.
::= { opticsIMIfEntry  37 }

--- BEGIN per-port capability
  opticsIMPortCapabilityIndex OBJECT-TYPE
  SYNTAX Integer32
  MAX-ACCESS read-write
  STATUS current
  DESCRIPTION
    "This attribute is a pointer to capability profile entries having 
	opticsIMCapabilityProfileProfIndex equal to opticsIMPortCapabilityIndex.
	The opticsIMCapabilityProfileTable contains information
	about capabilities supported by this interface.
    Default value is zero to indicate no capability profile is referenced."

::= { opticsIMIfEntry  38 }
--- END per-port capability

-- Begin OPTnm02313 
  opticsIMIfSwitchId OBJECT-TYPE
  SYNTAX INTEGER
  MAX-ACCESS read-write
  STATUS current
  DESCRIPTION
    "This attribute specifies the Ethernet Switch Instance this port belongs to ."

::= { opticsIMIfEntry  39 }

-- End OPTnm02313 

 opticsIMIfUserLabel OBJECT-TYPE
  SYNTAX  	OpticsIMUserLabel
    MAX-ACCESS read-write
    STATUS current
    DESCRIPTION
        "A textual string containing an Label provided by operator for this Interface."

::= { opticsIMIfEntry  40 }

-- Begin ONDnm09842 - P.Villa - V5.00.

opticsIMIfPortAlarmAdmin OBJECT-TYPE
  SYNTAX      INTEGER {
    ne-def(0),
    mon   (1),
    auto  (2)
  } 
  MAX-ACCESS  read-write
  STATUS      current
  DESCRIPTION
    "opticsIMIfPortAlarmAdmin  specifies 'on per port basis' Port Alarm Admin value
     according to below admitted values:
     - ne-def:    'on per NE basis' Alarm Admim Value (Default value)
     - mon:       this Port Alarm Admin value  takes as effect the ASAP is considered: 
                  the alarms emitted by that port are handled according to the pointed ASAP object
     - auto:      this Port Alarm Admin value takes as effect the ASAP (associated to that port) 
                  to be ignored: the alarms emitted by that port are inhibited independently 
                  on the pointed ASAP object  (via tsdimIfAsapIndex).
     "
::= { opticsIMIfEntry  41}

-- End ONDnm09842

-- Begin OPTnm20039 April 2013 for L3VPN
opticsIMIfIpIntfPointer OBJECT-TYPE
   SYNTAX  Unsigned32 (0..2147483647)
   MAX-ACCESS  read-write
   STATUS  current
   DESCRIPTION
   "the reference pointer of opticsIMVrfIpIntf index.
   The value 0 means that the interface is not IP. Value 0 is the default value"
::= { opticsIMIfEntry 42 }
-- End OPTnm20039 April 2013

-- Begin OPTnm23953 July 2013
opticsIMIfAlarmReeval OBJECT-TYPE
   SYNTAX  TruthValue
   MAX-ACCESS  read-write
   STATUS  current
   DESCRIPTION
   "This attribute triggers the interface alarm reevaluation. When this object is set to True the
    presence of the alarm is reconsidered, starting in any case from a not alarmed status.
    If the alarm conditions are matched then the alarm is raised, if it was already present the 
    alarm shall be maintained.
    Default value is False."
::= { opticsIMIfEntry 43 }
-- End OPTnm23953 July 2013

-- Begin OPTnm26463 
opticsIMIflnkaggThreshold OBJECT-TYPE
    SYNTAX     INTEGER
    MAX-ACCESS read-write
    STATUS     current
    DESCRIPTION
"Number of links considered in the detection of the LAG Excessive Bandwidth Degrade (dLAGEXBD) defect: 
if the number of LAG links, which are both attached from LACP perspective and working (i.e. not in failure condition), 
is lower than the opticsIMIflnkaggThreshold value and > 0 then the dLAGEXBD is detected.
The value of this object is meaningful only in case of LAG ifType.  Default value: 1"
  ::= { opticsIMIfEntry 44 }
-- End OPTnm26463 


opticsIMIf1588TCStatus OBJECT-TYPE
    SYNTAX INTEGER {
    notAplicable (0),
    active (1),
    notActive (2)}

     MAX-ACCESS read-only
     STATUS            current
     DESCRIPTION
         " This object contains the status of the  1588 Transparent Clock management related the this interface's entry.
The Transparent Clock is activated on 'NE basis' but each interface could be in a different status.
The 'notApplicable' value is returned when the interface doesn't support the management of the 1588 TC.
The 'active' value is returned when the interface is supporting the 1588 TC and the feature is actualy working on.
The 'notActive' value is returned when the interface is supporting the 1588 TC but the feature is not working due to some temporary conditions. 
         "
::= { opticsIMIfEntry 45 }



-- tsdimAlarmPlmRaise
tsdimAlarmPlmRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the Payload Mismatch (PLM) defect."
::= { tsdimSnmpNEMibObject 20 }

-- tsdimAlarmPlmClear
tsdimAlarmPlmClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the Payload Mismatch (PLM) defect clear."
::= { tsdimSnmpNEMibObject 21 }

-- opticsIMSdhIfTable
opticsIMSdhIfTable OBJECT-TYPE
  SYNTAX SEQUENCE OF OpticsIMSdhIfEntry
  MAX-ACCESS not-accessible
  STATUS current
  DESCRIPTION
    "This table contains the configuration of the server TTP.
     At startup or when a server TTP is deleted the objects assume the default 
     value."
::= { tsdimSnmpNEMibObject 22 }

opticsIMSdhIfEntry OBJECT-TYPE
  SYNTAX OpticsIMSdhIfEntry
  MAX-ACCESS not-accessible
  STATUS current
  DESCRIPTION
    ""
  INDEX { ifIndex }
::= { opticsIMSdhIfTable 1}

OpticsIMSdhIfEntry ::= SEQUENCE {
  opticsIMSdhIfSpeed Gauge32,
  opticsIMSdhIfUnderlieLayer INTEGER,
  opticsIMSdhIfType IANAifType,
  opticsIMSdhIfVcType INTEGER,
  opticsIMSdhIfCurrSpeed Gauge32
}

opticsIMSdhIfSpeed OBJECT-TYPE
  SYNTAX Gauge32
  MAX-ACCESS read-only
  STATUS current
  DESCRIPTION
    "Value of ifSpeed of the relative server TTP.
     The value 0 is the default.
     The change of this object is notified by an Attribute 
     Value Change (AVC) Notification. The value can be expressed in bit/s or 
     kbit/s NE dependent."
::= { opticsIMSdhIfEntry 1}

opticsIMSdhIfUnderlieLayer OBJECT-TYPE
  SYNTAX INTEGER { 
    sdh (1),
    pdh (2),
    none (3),
    mau (4),
    pconc (5),
    vconc (6) 
  }
  MAX-ACCESS read-only
  STATUS current
  DESCRIPTION
    "Type of the relative server TTP (SDH or PDH).
     The value none is the default.
     The change of this object is notified by an Attribute Value Change (AVC) 
     Notification."
::= { opticsIMSdhIfEntry 2}

opticsIMSdhIfType OBJECT-TYPE
  SYNTAX IANAifType
  MAX-ACCESS read-only
  STATUS current
  DESCRIPTION
    "Type of the interface associated with the server TTP.
     The value other (1) is the default and applies when no interface type is 
     associated with the server TTP.
     The change of this object is notified by an Attribute Value Change 
     Notification."
::= { opticsIMSdhIfEntry 3 }

opticsIMSdhIfVcType OBJECT-TYPE
  SYNTAX INTEGER {
    other (1),
    vc12 (2),
    vc3 (3),
    vc4 (4),
    vc4-4c (5),
    vt1-5 (6),
    sts-1 (7),
    sts-3c (8),
    sts-12c (9),
    sts-192c (10),
    vt-2 (11),
    vt-3 (12),
    vt-6 (13),
    pdh-e1 (14),
    pdh-ds1 (15),
    pdh-e3 (16),
    pdh-ds3 (17)
  }
  MAX-ACCESS read-only
  STATUS current
  DESCRIPTION
    "Type of the underlying SDH VC.
     The value other (1) is the default and applies to the case where the 
     underlying layer is not SDH/SONET/PDH or PCONC.

     The other values (vc12,vc3,vc4,vc4-4c) apply only when the underlying 
     layer is SDH or PCONC.
     The values (vt1-5, sts-1, sts-3c, sts-12c, sts-192c, vt-2, vt-3, vt-6 )
     are applicable when the underlying layer is SONET or PCONC.

     The values (pdh-e1, pdh-ds1, pdh-e3, pdh-ds3 ) are applicable are 
     applicable when the underlying layer is PDH or PCONC.

     The change of this object is notified by an Attribute Value Change 
     Notification."
::= { opticsIMSdhIfEntry 4}

opticsIMSdhIfCurrSpeed OBJECT-TYPE
  SYNTAX Gauge32
  MAX-ACCESS read-only
  STATUS current
  DESCRIPTION
    "Value of actual ifSpeed of the relative server TTP.
     The value of the opticsIMSdhIfSpeed is the default.
     When the underlying layer is PCONC or VCONC it represents the number of 
     active and working VCs in the virtual or packet concatenated Group and 
     therefore it could be lower than the opticsIMSdhIfSpeed.

     The change of this object is notified by an Attribute Value Change (AVC) 
     Notification. The value can be expressed in bit/s or kbit/s NE dependent"
::= { opticsIMSdhIfEntry 5 }

-- opticsIMAlarmTsfRaise
tsdimAlarmTsfRaise NOTIFICATION-TYPE
  OBJECTS {
    tsdimEventObjectClassIdentifier,
    tsdimEventObjectInstanceIdentifier,
    tsdimEventNotificationId,        
    tsdimEventTime,        
    tsdimAlarmSeverity,        
    tsdimAlarmSpecProblem,
    opticsIMAdditionalText,
    opticsIMAlarmType
  }
  STATUS current
  DESCRIPTION         
    "This notification reports TSF alarm."
::= { tsdimSnmpNEMibObject 23 }

-- opticsIMAlarmTsfClear

tsdimAlarmTsfClear NOTIFICATION-TYPE
  OBJECTS {
    tsdimEventObjectClassIdentifier,
    tsdimEventObjectInstanceIdentifier,
    tsdimEventNotificationId,        
    tsdimEventTime,        
    tsdimAlarmSeverity,
    tsdimAlarmSpecProblem,
    opticsIMAdditionalText,
    opticsIMAlarmType
  }
  STATUS current    
  DESCRIPTION
    "This notification reports TSF alarm clear."
::= { tsdimSnmpNEMibObject 24 }

-- opticsimEpsConfStatus
opticsimEpsConfStatus OBJECT-TYPE
  SYNTAX TruthValue
  MAX-ACCESS read-only
  STATUS current
  DESCRIPTION
    "This object reports information about the EPS (Equipment Protection 
     Switching) configuration of an ISA board.
     If the ISA board does not support plug-able access card, this object 
     becomes true if and only if the ISA board is EPS protected.
     If the ISA board supports plug-able access card, this object becomes true 
     if and only if the ISA board is EPS protected and both the main and the 
     spare boards are equipped with the same access card."
::= { tsdimSnmpNEMibObject 31 }


-- opticsimEpsActiveRole

opticsimEpsActiveRole OBJECT-TYPE
  SYNTAX INTEGER {
    main (1),
    spare (2)
  }
  MAX-ACCESS read-only
  STATUS current
  DESCRIPTION
    "This object report the role (i.e. main or spare) of the active ISA board. 
     This object is meaningful only if the opticsimEpsConfStatus is true.
     Otherwise, the value main (1) is always returned."
::= { tsdimSnmpNEMibObject 32 }

-- opticsimIsaAccess

opticsimIsaAccess OBJECT-TYPE
  SYNTAX Unsigned32
  MAX-ACCESS read-only
  STATUS current
  DESCRIPTION
    "This object report the access card equipped in the Equipment domain for 
     the ISA board.
     The value 0 (unknown) is the default value for the following cases:
     - the ISA board does not support equipped access card (e.g. because it is 
       plugged in an old equipment)
     - the access card in is not known by the ISA board (e.g. it is not a 
       14xFE nor a 4xGE)
     The value 1 (none) is used to report that no access card has been equipped.

     The other values (>1) represent the access card that was  equipped.
     The association between the value of this object and the access card is 
     product specific and will be documented in the product external 
     specification"
::= { tsdimSnmpNEMibObject 33 }

-- opticsimSwPackageProfile

opticsimSwPackageProfile OBJECT-TYPE
  SYNTAX BITS {
    sdh(0),
    wdm(1),
    ethernet(2),
    mpls(3),
    cp(4),
    spare1(5),
    spare2(6),
    spare3(7)  
  }
  MAX-ACCESS read-only
  STATUS current
  DESCRIPTION
    "This object is used for reporting the software package profile which 
     indicates the network functionalities enabled on the NE.

     The value of this attribute is commonly agreed, its semantic will be 
     described in the relevant Ext. Interface Management Specification."
::= { tsdimSnmpNEMibObject 35 }

-- opticsimNeAutoProvisioning
opticsimNeAutoProvisioning OBJECT-TYPE
  SYNTAX INTEGER {
    fullPlugAndPlay(1),
    noPlugAndPlay (2),
    confirmedPlugAndPlay (3) }
  MAX-ACCESS read-write
  STATUS current
  DESCRIPTION
    "This object allows the manager to set the way of physical item provisioning
     on the NE.
     The Full Plug&Play value will set the automatic provisioning without 
     manager intervention.
     The No Plug&Play value will set the provisioning full in the hands of 
     manager.
     The Confirmed Plug&Play value (that is the default value) will cause the 
     agent to ask for manager confirmation before provisioning.
     The confirmation request to operator by manager (in the confirmed plug 
     and play case), is activated by an Attribute Value Change (AVC) associated 
     to the change of the opticsEquipmentActual object value in the 
     OPTICSIM-EQPT-MIB"
::= { tsdimSnmpNEMibObject 36 }

-- opticsIMNePMCollection

opticsIMNePMCollection OBJECT IDENTIFIER ::= { tsdimSnmpNEMibObject 37 }

-- Start Objects related to  opticsIMNePMCollection
-- opticsIMNePMCollectionStatus

opticsIMNePMCollectionStatus OBJECT-TYPE
  SYNTAX INTEGER {
    readyForRequest(1),
    inPreparation(2),
    fileTransferCompleted(3)
  }
  MAX-ACCESS read-only
  STATUS current
  DESCRIPTION
    "This object defines the PM collection NE status: three operating status 
     have been defined:
       the <Ready_for_Request> status,
       the <In_Preparation> status,
       the <fileTransferCompleted> status;
       the default status is the <fileTransferCompleted> one."
::= { opticsIMNePMCollection 1 }

-- opticsIMNePMActivateCollection

opticsIMNePMActivateCollection OBJECT-TYPE
  SYNTAX INTEGER {
    noop(1),
    normalStart(2),
    forcedStart(3) 
  }
  MAX-ACCESS read-write
  STATUS current
  DESCRIPTION
    "This object defines the start of the PM collection on the NE: the value 
     <NormalStart> can be set by manager when he want to activate the PM 
     collection in normal condition; the value <ForcedStart> can be set by 
     manager when he want to activate the PM collection in abnormal condition 
     (for instance when NE is still preparing a previous commanded PM 
     collection); the agent will reset the value to <Noop> when the manager 
     setting has been recognized.
     The default value is the <Noop> one."
::= { opticsIMNePMCollection 2 }

-- opticsIMNePMTimePeriodCollection
opticsIMNePMTimePeriodCollection OBJECT-TYPE
  SYNTAX OpticsIMPmPeriodTime
  MAX-ACCESS read-write
  STATUS current
  DESCRIPTION
    "This object defines the time value before which no hystorical data must be 
     considered for the PM collection file. The default value, that is the null 
     value (i.e. 0), represents the maximum allowed for that application."
::= { opticsIMNePMCollection 3 }

-- End Objects related to  opticsIMNePMCollection

opticsIMMibConfigurationMode OBJECT-TYPE
  SYNTAX OpticsIMMibConfigurationMode
  MAX-ACCESS read-write
  STATUS current
  DESCRIPTION
    "This attribute defines the possibility to 'isolate' (offline) the MIB 
     configuration from the HW Configuration inside the NE.
     This means both that, at the management interface, requests are not 
     propagated to the HW and alarms are not reported.
     Default value (online) can be changed only in case of MIB Restore
     procedure."
::= { tsdimSnmpNEMibObject 38 }

-- opticsIMdatabaseModify
opticsIMdatabaseModify OBJECT-TYPE
  SYNTAX TsdimEventTimeInt
  MAX-ACCESS read-only
  STATUS current
  DESCRIPTION
    "This attribute stores the information that a local operator has changed 
     the configuration in a persistent way.
     It contains the date of the last time the LAC status has become granted."
::= { tsdimSnmpNEMibObject 41 }

-- opticsimSwPackageProfileRequested

opticsimSwPackageProfileRequested OBJECT-TYPE
  SYNTAX BITS {
    sdh(0),
    wdm(1),
    ethernet(2),
    mpls(3),
    cp(4),
    spare1(5),
    spare2(6),
    spare3(7)
  }
  MAX-ACCESS read-write
  STATUS current
  DESCRIPTION
    "This object is used for configuring the software package profile which 
     indicates the network functionalities enabled on the NE. If the requested 
     profile is compatible with the downloaded software, the configuration is 
     accepted, the value is saved in the boot NE area and, when the NE has been
     restarted, the value will be effective and it will be mirrored in the 
     opticsimSwPackageProfile, otherwise the error code badValue has to be 
     returned.
     The value of this attribute is commonly agreed, its semantic will be 
     described in the relevant Ext. Interface Management Specification."
::= { tsdimSnmpNEMibObject 42 }

-- opticsIMPoolTable

opticsIMPoolTable OBJECT-TYPE
  SYNTAX SEQUENCE OF OpticsIMPoolEntry
  MAX-ACCESS not-accessible
  STATUS current
  DESCRIPTION
    "This table defines the pools available in the node. The following pools are defined:

      poolID      pool      poolDescription
      --------------------------------------------------------------------
      1           Pool1     Packet Processor Bandwidth (kbit)
      2           Pool2     Packet Processor CAM (Number of entries)
      3           Pool3     Traffic Manager Logical Ports (number of ports)
      4           Pool4     Traffic Descriptors (number of TD)
      5           Pool5     InFlows (number of flows)
      6           Pool6     OutFlows (number of flows)
      7           Pool7     CrossConnections (number of XC)
      8           Pool8     Link Aggregation Groups (number of LAG)
      9           Pool9     Spanning Tree Instances (number of instances)
      10          Pool10    Matrix channels (number of channels)
      11          Pool11    Bandwidth for Remote Ports
      12          Pool12    Ethernet classifiers (number of ETS Classifiers)
      13          Pool13    Static VLAN registration entries (number of 
                            registered VLANs)
      14          Pool14    (IVL/SVL)Dynamic Filtering Entries (number of 
                            dynamic entries)
      15          Pool15    (IVL/SVL)Static Filtering Entries (number of static
                            entries)
      16          Pool16    IGMP Snooping Entries (number of IGMP Snooping 
                            Entries)
      17          Pool17    MPLS InSegments (number of MPLS InSegments)
      18          Pool18    MPLS OutSegments (number of MPLS OutSegments)
      19          Pool19    MPLS Tunnels (number of MPLS Tunnels)
      20          Pool20    MPLS Traffic Descriptors (number of MPLS Traffic 
                            Descriptors)"
::= { tsdimSnmpNEMibObject 43 }

opticsIMPoolEntry OBJECT-TYPE
  SYNTAX OpticsIMPoolEntry
  MAX-ACCESS not-accessible
  STATUS current
  DESCRIPTION
    "Each entry is a resource pool associated to a defined position (open to be
     extended).
     Description of entries:
     -  positionID: it is the physical position of the board (e.g. slot). It is
        used as entry for the resources associated for example to the board 
        configured in a slot. It is used positionID 0.0.0.0.0 (zero) to indicate
        pools for the whole Network element.
     -  poolID: it is a unique identifier describing the pool; the association 
        poolID - pool descriptor is provided in the behaviour.
     -  nominalResources: the maximum number of resources available (by 
        definition)
     -  UsedResources: the number of used resources
     -  availableResources: the current available resources (it's the nominal 
        subtracted the used).
     -  crossRelation: it is a field used when different items in the network 
        element (e.g. different boards) share the same pools of resources. The 
	typical case is when Access Card (providing physical access) are used. 
	In this case the same pool information is repeated for the slots 
	containing the main board and the access card itself and in 
	correspondence to the access card slot entries, the crossRelation field 
	indicates the slot related to the corresponding main board (and it is 
	indicated also in correspondence of the main board crossRelation).
    "
    INDEX { opticsIMpositionID, opticsIMpoolID }
::= { opticsIMPoolTable 1 }

OpticsIMPoolEntry ::= SEQUENCE {
  opticsIMpositionID             OCTET STRING,
  opticsIMpoolID                 Integer32, 
  opticsIMPoolnominalResources   Integer32,
  opticsIMPoolusedResources      Integer32,
  opticsIMPoolavailableResources Integer32,
  opticsIMPoolcrossRelation      OCTET STRING
}

opticsIMpositionID OBJECT-TYPE
  SYNTAX OCTET STRING
  MAX-ACCESS not-accessible
  STATUS current
  DESCRIPTION
    "This object defines the physical position of the board referenced by the 
     pool."
::= { opticsIMPoolEntry 1 }

opticsIMpoolID OBJECT-TYPE
  SYNTAX Integer32
  MAX-ACCESS not-accessible
  STATUS current
  DESCRIPTION
    "This object defines the unique identifier describing the pool."
::= { opticsIMPoolEntry 2 }

opticsIMPoolnominalResources OBJECT-TYPE
  SYNTAX Integer32
  MAX-ACCESS read-only
  STATUS current
  DESCRIPTION
    "This object indicates the maximum number of resources available."
::= { opticsIMPoolEntry 3 }

opticsIMPoolusedResources OBJECT-TYPE
  SYNTAX Integer32
  MAX-ACCESS read-only
  STATUS current
  DESCRIPTION
    "This object indicates the number of used resources."
::= { opticsIMPoolEntry 4 }

opticsIMPoolavailableResources OBJECT-TYPE
  SYNTAX Integer32
  MAX-ACCESS read-only
  STATUS current
  DESCRIPTION
    "This object indicates the current available resources."
::= { opticsIMPoolEntry 5 }

opticsIMPoolcrossRelation OBJECT-TYPE
  SYNTAX OCTET STRING
  MAX-ACCESS read-only
  STATUS current
  DESCRIPTION
    "This object is used when different items in the network element (e.g.
     different boards) share the same pools of resources. The typical case is 
     when Access Card (providing physical access) are used. In this case the 
     same pool information is repeated for the slots containing the main board 
     and the access card itself and in correspondence to the access card slot 
     entries, the crossRelation field indicates the slot related to the 
     corresponding main board (and it is indicated also in correspondence of 
     the main board crossRelation)the current available resources."
::= { opticsIMPoolEntry 6 }

-- opticsimNeMtu

opticsimNeMtu OBJECT-TYPE
  SYNTAX Unsigned32
  MAX-ACCESS read-write
  STATUS current
  DESCRIPTION
    "This object reports 'on per NE basis' MTU (the size of the largest packet 
     which can be sent/received on NE) specified in octets. For NE interfaces 
     that are used for transmitting network datagrams, this is the size of the 
     largest network datagram that can be sent on any NE interface.
     'on per NE basis' MTU is mutually exclusive with 'on per port basis' MTU 
     and is supported ONLY on NE without 'on per port basis' MTU provisioning.
     The value 0 (unknown) is the default value (with the meaning of no 'on 
     per NE basis' MTU value).
     The support of 'on per NE basis' MTU is product specific and will be 
     documented in the product external specification"
::= { tsdimSnmpNEMibObject 44 }

-- TSDIM-SNMPNE-MIB opticsIMNeMACCollection

opticsIMNeMACCollection OBJECT IDENTIFIER ::= { tsdimSnmpNEMibObject 45 }

-- Start Objects related to  opticsIMNeMACCollection
-- opticsIMNeMACCollectionStatus

opticsIMNeMACCollectionStatus OBJECT-TYPE
  SYNTAX INTEGER {
    readyForRequest(1),
    inPreparation(2),
    fileTransferCompleted(3) 
  }
  MAX-ACCESS read-only
  STATUS current
  DESCRIPTION
    "This object defines the MAC collection NE status:
       2 operating status have been defined:
         the <Ready_for_Request> status,
         the <In_Preparation> status and
         the <File_Transfer_Completed> status;
         the default status is <Ready_for_Request>"
::= { opticsIMNeMACCollection 1 }

-- opticsIMNeMACActivateCollection

opticsIMNeMACActivateCollection OBJECT-TYPE
  SYNTAX INTEGER {
    noop(1),
    normalStart(2),
    forcedStart(3) }
  MAX-ACCESS read-write
  STATUS current
  DESCRIPTION
    "This object defines the start of the MAC collection on NE: the value 
     <NormalStart> is set by manager in order to activate the MAC collection 
     in normal condition; the value <ForcedStart> is set by manager in order to
     activate the MAC collection in
        abnormal condition (for instance when NE is still
        preparing a previous commanded MAC collection);
        the agent will reset the value to <Noop>
        when the manager setting has been recognized.
        The default value is the <Noop> one."
::= { opticsIMNeMACCollection 2 }

-- opticsIMNeConfigurationType

opticsIMNeConfigurationType OBJECT-TYPE
    SYNTAX DisplayString
    MAX-ACCESS read-only
    STATUS current
    DESCRIPTION
        "This object defines the NE configuration type requested
         by the managing system."
::= { opticsIMNeConfiguration 1 }

-- opticsIMNeConfigurationTypeId

opticsIMNeConfigurationTypeId OBJECT-TYPE
    SYNTAX Integer32
    MAX-ACCESS read-write
    STATUS current
    DESCRIPTION
        "This object defines the identifier of the NE configuration type
         requested by the managing system. This identifier must be included
         in one of the entries of the 
         opticsIMAllowedNeConfigurationTypeTable.
         As a side effect of setting this object, the agent must set the
         opticsIMNeConfigurationType object with the string associated to
         this identifier."
::= { opticsIMNeConfiguration 2 }

-- opticsIMAllowedNeConfigurationTypeTable

opticsIMAllowedNeConfigurationTypeTable OBJECT-TYPE
  SYNTAX SEQUENCE OF OpticsIMAllowedNeConfigurationTypeEntry
  MAX-ACCESS         not-accessible
  STATUS             current
  DESCRIPTION
    "This table contains all the configurations types allowed for the 
     supported NE."
::= {  opticsIMNeConfiguration 3 }

opticsIMAllowedNeConfigurationTypeEntry OBJECT-TYPE
  SYNTAX      OpticsIMAllowedNeConfigurationTypeEntry
  MAX-ACCESS  not-accessible
  STATUS      current
  DESCRIPTION
    "An entry of the allowed Ne configuration types table. 
     Each entry (row) corresponds to a configuration type allowed for the NE."
    INDEX    { opticsIMAllowedNeConfigurationId  }
::= { opticsIMAllowedNeConfigurationTypeTable 1 } 

OpticsIMAllowedNeConfigurationTypeEntry ::= SEQUENCE {
  opticsIMAllowedNeConfigurationId   Integer32,
  opticsIMAllowedNeConfigurationType DisplayString
}

opticsIMAllowedNeConfigurationId OBJECT-TYPE
  SYNTAX     Integer32
  MAX-ACCESS not-accessible
  STATUS     current
  DESCRIPTION
    "This object contains the identifier associated to a NE configuration type. 
     It identifies the index of the table."
::= { opticsIMAllowedNeConfigurationTypeEntry 1 }

opticsIMAllowedNeConfigurationType OBJECT-TYPE
  SYNTAX     DisplayString
  MAX-ACCESS read-only
  STATUS     current
  DESCRIPTION
    "This object identifies an allowed configuration type of the NE."
::= { opticsIMAllowedNeConfigurationTypeEntry 2 }

-- opticsIMMarket

opticsIMMarket OBJECT-TYPE
  SYNTAX  INTEGER { 
    etsi (1),
    ansi (2) }
  MAX-ACCESS read-write
  STATUS current
  DESCRIPTION
    "This object specifies the application market. With this information the 
     agent will be able to provide to the manager only the configurations 
     consistent with the market defined."
::= { opticsIMNeConfiguration 4 }

-- opticsIMNeEquipmentName

opticsIMNeEquipmentName OBJECT-TYPE
  SYNTAX DisplayString
  MAX-ACCESS read-only
  STATUS current
  DESCRIPTION
    "This scalar object defines in synthesis the NE characteristics (NE name, 
     frequency, configuration type, modulation,capability...)"
::= { opticsIMNeConfiguration 5 }

--  opticsIMAllowedNePeripheralTable

opticsIMAllowedNePeripheralTable OBJECT-TYPE
  SYNTAX SEQUENCE OF OpticsIMAllowedNePeripheralEntry
  MAX-ACCESS                       not-accessible
  STATUS                   current
  DESCRIPTION
    "This table contains all the peripherals (type and configuration) allowed 
     for each configuration Ne allowed on the NE."
::= {  opticsIMNeConfiguration 6 }

opticsIMAllowedNePeripheralEntry OBJECT-TYPE
  SYNTAX     OpticsIMAllowedNePeripheralEntry
  MAX-ACCESS not-accessible
  STATUS     current
  DESCRIPTION
    "An entry of the allowed NE peripherals table. Each entry (row) corresponds 
     to an allowed peripheral type and peripheral configuration for each 
     configuration type Ne allowed for the NE "
  INDEX { opticsIMAllowedNeConfigurationId, opticsIMAllowedNePeripheralId}
::= { opticsIMAllowedNePeripheralTable 1 }

OpticsIMAllowedNePeripheralEntry ::= SEQUENCE {
  opticsIMAllowedNePeripheralId            Integer32,
  opticsIMAllowedNePeripheralType          DisplayString,
  opticsIMAllowedNePeripheralConfiguration DisplayString
}

opticsIMAllowedNePeripheralId OBJECT-TYPE
  SYNTAX     Integer32
  MAX-ACCESS not-accessible
  STATUS     current
  DESCRIPTION
    "This object contains the identifier associated to a peripheral type and 
     peripheral configuration.
     It identifies the index of the table."
::= { opticsIMAllowedNePeripheralEntry 1 }

opticsIMAllowedNePeripheralType OBJECT-TYPE
  SYNTAX     DisplayString
  MAX-ACCESS read-only
  STATUS     current
  DESCRIPTION
    "This object identifies an allowed peripheral type."
::= { opticsIMAllowedNePeripheralEntry 2 }

opticsIMAllowedNePeripheralConfiguration OBJECT-TYPE
  SYNTAX     DisplayString
  MAX-ACCESS read-only
  STATUS     current
  DESCRIPTION
    "This object identifies an allowed configuration  type of the peripheral."
::= { opticsIMAllowedNePeripheralEntry 3 }

--  opticsIMNeTrsDirectionTable
opticsIMNeTrsDirectionTable    OBJECT-TYPE
  SYNTAX SEQUENCE OF OpticsIMNeTrsDirectionEntry
  MAX-ACCESS         not-accessible
  STATUS             current
  DESCRIPTION
    "This table contains the parameters associated to the transmission 
     directions on NE.
     A transmission direction connects the NE to an adjacent NE by a specific 
     transmission interface (i.e. radio, PDH)"
::= {  opticsIMNeConfiguration 7 }

opticsIMNeTrsDirectionEntry OBJECT-TYPE
  SYNTAX     OpticsIMNeTrsDirectionEntry
  MAX-ACCESS not-accessible
  STATUS     current
  DESCRIPTION
    "An entry of the direction table.
     Each entry (row) corresponds to a specific direction."
  INDEX    { opticsIMNeTrsDirectionIndex}
::= { opticsIMNeTrsDirectionTable 1 } 

OpticsIMNeTrsDirectionEntry ::= SEQUENCE {
  opticsIMNeTrsDirectionIndex           Integer32,
  opticsIMNeTrsDirectionConfigurationId Integer32,
  opticsIMNeTrsDirectionMaxCapacity     DisplayString,
  opticsIMNeTrsDirectionRole            DisplayString,
  opticsIMNeTrsDirectionRowStatus       RowStatus
}

opticsIMNeTrsDirectionIndex OBJECT-TYPE
  SYNTAX Integer32
  MAX-ACCESS not-accessible
  STATUS current
  DESCRIPTION
    "This object contains the identifier associated to a transmission direction
     to/from an adjacent NE.
     It identifies the index of the table."
::= { opticsIMNeTrsDirectionEntry 1 }

opticsIMNeTrsDirectionConfigurationId       OBJECT-TYPE
  SYNTAX Integer32
  MAX-ACCESS read-create
  STATUS current
  DESCRIPTION
    "This object defines the identifier of the NE configuration type requested 
     by the managing system on this direction. Thid identifier must be included 
     in one of the entries of the opticsIMAllowedNeConfigurationTypeTable."
::= { opticsIMNeTrsDirectionEntry 2 }

opticsIMNeTrsDirectionMaxCapacity OBJECT-TYPE
  SYNTAX     DisplayString
  MAX-ACCESS read-only
  STATUS     current
  DESCRIPTION
    "This object contains the maximum transmission capacity on this direction.
     It is updated by managed system (agent) after configuration of transmission 
     capacity for each interface (i.e. radio, PDH on each specific object) 
     belonging to this direction."
::= { opticsIMNeTrsDirectionEntry 3 }

opticsIMNeTrsDirectionRole OBJECT-TYPE
  SYNTAX DisplayString
  MAX-ACCESS read-create
  STATUS current
  DESCRIPTION
    "This object reports a specific behaviour for this direction. It is used to 
    differ the behaviour of this direction from the behaviour of the other 
    directions. The content is defined in each  product specification."
::= { opticsIMNeTrsDirectionEntry 4 }

opticsIMNeTrsDirectionRowStatus  OBJECT-TYPE
  SYNTAX RowStatus
  MAX-ACCESS read-create
  STATUS current
  DESCRIPTION
    "See textual convention."
::= { opticsIMNeTrsDirectionEntry 5 }

-- opticsIMDirectionInterfaceTable

opticsIMNeDirectionPeripheralTable    OBJECT-TYPE
  SYNTAX SEQUENCE OF OpticsIMNeDirectionPeripheralEntry
  MAX-ACCESS         not-accessible
  STATUS             current
  DESCRIPTION
    "This table contains all the peripheral (type and configuration) selected 
     for each direction on the NE."
::= {  opticsIMNeConfiguration 8 }

opticsIMNeDirectionPeripheralEntry OBJECT-TYPE
  SYNTAX     OpticsIMNeDirectionPeripheralEntry
  MAX-ACCESS not-accessible
  STATUS     current
  DESCRIPTION
    "An entry of direction table.
     Each entry (row) corresponds to a selected peripheralId for each direction"
  INDEX {opticsIMNeTrsDirectionIndex, opticsIMNeDirectionPeripheralIndex}
::= { opticsIMNeDirectionPeripheralTable  1 } 

OpticsIMNeDirectionPeripheralEntry ::= SEQUENCE {
  opticsIMNeDirectionPeripheralIndex         Integer32,
  opticsIMNeDirectionPeripheralId            Integer32,
  opticsIMNeDirectionPeripheralType          DisplayString,
  opticsIMNeDirectionPeripheralConfiguration DisplayString,
  opticsIMNeDirectionPeripheralRowStatus     RowStatus
}

opticsIMNeDirectionPeripheralIndex OBJECT-TYPE
  SYNTAX Integer32
  MAX-ACCESS not-accessible
  STATUS current
  DESCRIPTION
    "This object contains the index of a peripheral identifier selected on a
     direction. 
     It identifies the index of the table."
::= { opticsIMNeDirectionPeripheralEntry 1 }

opticsIMNeDirectionPeripheralId OBJECT-TYPE
  SYNTAX     Integer32
  MAX-ACCESS read-create
  STATUS     current
  DESCRIPTION
    "This object defines the identifier of the peripheral type and peripheral 
     configuration requested by the managing systems.

     This identifier must be included in one of the 
     opticsIMAllowedNePeripheralTable associated to the 
     opticsIMNeTrsDirectionConfigurationId object on 
     opticsIMNeTrsDirectionTable.

     As a side effect of setting this object, the agent must set the 
     opticsIMNeDirectionPeripheralType object and the 
     opticsIMNeDirectionPeripheralConfiguration object with the strings 
     associated."
::= { opticsIMNeDirectionPeripheralEntry 2 }

opticsIMNeDirectionPeripheralType OBJECT-TYPE
  SYNTAX     DisplayString
  MAX-ACCESS read-only
  STATUS     current
  DESCRIPTION
    "This object defines a pheripheral type requested by the managing system on
     a direction."
::= { opticsIMNeDirectionPeripheralEntry 3 }

opticsIMNeDirectionPeripheralConfiguration   OBJECT-TYPE
  SYNTAX     DisplayString
  MAX-ACCESS read-create
  STATUS     current
  DESCRIPTION
    "This object defines a pheripheral configuration requested by the managing 
     system on a direction."
::= { opticsIMNeDirectionPeripheralEntry 4 }

opticsIMNeDirectionPeripheralRowStatus  OBJECT-TYPE
  SYNTAX RowStatus
  MAX-ACCESS read-create
  STATUS current
  DESCRIPTION
    "See  textual convention."
::= { opticsIMNeDirectionPeripheralEntry 5 }

-- opticsIMNeCompositionIndexNext

opticsIMNeCompositionIndexNext OBJECT-TYPE
  SYNTAX Unsigned32 (0..2147483647)
  MAX-ACCESS read-only
  STATUS current
  DESCRIPTION
    "This object contains an appropriate value to be used for
     opticsIMNeCompositionIndex when creating entries in the 
     opticsIMNeCompositionTable. The value 0 indicates that no unassigned 
     entries are available. To obtain the opticsIMNeCompositionIndex value for 
     a new entry, the manager issues a management protocol retrieval operation 
     to obtain the current value of this object. After each retrieval, the 
     agent should modify the value to the next unassigned index.

     After a manager retrieves a value, the agent will determine through its 
     local policy when this index value will be made available for reuse."
::= {  opticsIMNeConfiguration 10 }

-- opticsIMNeCompositionTable

opticsIMNeCompositionTable    OBJECT-TYPE
   SYNTAX SEQUENCE OF OpticsIMNeCompositionEntry
   MAX-ACCESS                       not-accessible
   STATUS                   current
   DESCRIPTION
      "This table contains the composition of the NE in term of NE configuration 
       type requested by the managing system. "
::= {  opticsIMNeConfiguration 9 }

opticsIMNeCompositionEntry OBJECT-TYPE
  SYNTAX                   OpticsIMNeCompositionEntry
  MAX-ACCESS                       not-accessible
  STATUS                   current
  DESCRIPTION
    "An entry of the NE composition table.  
     Each entry (row) corresponds to a configuration type allowed for the NE."
  INDEX    { opticsIMNeCompositionIndex  }
::= { opticsIMNeCompositionTable    1 } 

OpticsIMNeCompositionEntry::= SEQUENCE {
  opticsIMNeCompositionIndex             Integer32,
  opticsIMNeCompositionConfigurationId   Integer32,
  opticsIMNeCompositionConfigurationType DisplayString,
  opticsIMNeCompositionRowStatus         RowStatus
  }

opticsIMNeCompositionIndex             OBJECT-TYPE
  SYNTAX Integer32
  MAX-ACCESS not-accessible
  STATUS current
  DESCRIPTION
    "This object contains the index of the table."
::= { opticsIMNeCompositionEntry 1 }

opticsIMNeCompositionConfigurationId   OBJECT-TYPE
  SYNTAX Integer32
  MAX-ACCESS read-create
  STATUS current
  DESCRIPTION
    "This object defines a identifier of the NE configuration type requested 
     by the managing system.
     This identifier must be included in one of the entries of the 
     opticsIMAllowedNEConfigurationTypeTable.
     As a side effect of this setting, the agent must set the 
     opticsIMNeCompositionConfigurationType object with the string associated 
     to this identifier."
::= { opticsIMNeCompositionEntry 2 }

opticsIMNeCompositionConfigurationType OBJECT-TYPE
  SYNTAX DisplayString
  MAX-ACCESS read-only
  STATUS current
  DESCRIPTION
    "This object defines a NE configuration type requested by the managing 
     system."
::= { opticsIMNeCompositionEntry 3 }

opticsIMNeCompositionRowStatus         OBJECT-TYPE
  SYNTAX RowStatus
  MAX-ACCESS read-create
  STATUS current
  DESCRIPTION
    "See  textual convention."
::= { opticsIMNeCompositionEntry 4 }

-- opticsIMProtectionConfigurationTable  

opticsIMProtectionIndexNext OBJECT-TYPE
  SYNTAX Unsigned32 (0..2147483647)
  MAX-ACCESS read-only
  STATUS current
  DESCRIPTION
    "This object contains an appropriate value to be used for 
     opticsIMProtectionConfigurationIndex when creating entries in the 
     opticsIMProtectionConfigurationTable. The value 0 indicates that no 
     unassigned entries are available. To obtain the 
     opticsIMProtectionConfigurationIndex value for a new entry, the manager 
     issues a management protocol retrieval operation  to obtain the current 
     value of this object. After each retrieval, the agent should modify the 
     value to the next unassigned index.
     After a manager retrieves a value, the agent will determine through its 
     local policy when this index value will be made available for reuse."
::= { opticsIMNeConfiguration 11 }

opticsIMProtectionConfigurationTable    OBJECT-TYPE
  SYNTAX SEQUENCE OF OpticsIMProtectionConfigurationEntry
  MAX-ACCESS                       not-accessible
  STATUS                   current
  DESCRIPTION
    "This table allows the managing system to define the protection type on 
     equipment provisioning in order to create the protection schemes. 
     It is indexed by the equipment position, related to equipmentTable, 
     involved in the protection scheme"
::= { opticsIMNeConfiguration 12 }

opticsIMProtectionConfigurationEntry OBJECT-TYPE
  SYNTAX                OpticsIMProtectionConfigurationEntry
  MAX-ACCESS            not-accessible
  STATUS                current
  DESCRIPTION
    "An entry of the protection configuration table.  
       Each entry (row) corresponds to a Protection type involving 2 equipment position on equipmentTable."
  INDEX    { opticsIMProtectionConfigurationIndex }
::= { opticsIMProtectionConfigurationTable    1 } 

OpticsIMProtectionConfigurationEntry::= SEQUENCE {
   opticsIMProtectionConfigurationIndex            Unsigned32,
   opticsIMProtectionEqptPositionMain              OCTET STRING,
   opticsIMProtectionEqptPositionSpare             OCTET STRING,
   opticsIMProtectionType                          DisplayString,
   opticsIMProtectionRowStatus                     RowStatus,
   opticsIMProtectionTypeId                        Integer32
   }

opticsIMProtectionConfigurationIndex            OBJECT-TYPE
  SYNTAX Unsigned32
  MAX-ACCESS not-accessible
  STATUS current
  DESCRIPTION
    "This object contains the index of the table.
     It contains the value retrieved from agent by a GET request on 
     opticsIMProtectionIndexNext object."
::= { opticsIMProtectionConfigurationEntry 1 }

opticsIMProtectionEqptPositionMain             OBJECT-TYPE
  SYNTAX OCTET STRING (SIZE(4))
  MAX-ACCESS read-create
  STATUS current
  DESCRIPTION
    "This object contains the index of the table.
     It contains the same value of equipmentPosition index on 
     OpticsIMEquipmentEntry that the managing system requires involved in a 
     protection scheme."
::= { opticsIMProtectionConfigurationEntry 2 }

opticsIMProtectionEqptPositionSpare             OBJECT-TYPE
  SYNTAX OCTET STRING (SIZE(4))
  MAX-ACCESS read-create
  STATUS current
  DESCRIPTION
    "This object contains the index of the table.
     It contains the same value of equipmentPosition index on 
     OpticsIMEquipmentEntry that the managing system requires involved in a 
     protection scheme."
::= { opticsIMProtectionConfigurationEntry 3 }

opticsIMProtectionType OBJECT-TYPE
  SYNTAX DisplayString
  MAX-ACCESS read-create
  STATUS current
  DESCRIPTION
    "This object defines the protection for the equipment related to this 
     postion."
::= { opticsIMProtectionConfigurationEntry 4 }

opticsIMProtectionRowStatus     OBJECT-TYPE
  SYNTAX RowStatus
  MAX-ACCESS read-create
  STATUS current
  DESCRIPTION
    "See textual convention."
::= { opticsIMProtectionConfigurationEntry 5 }

opticsIMProtectionTypeId   OBJECT-TYPE
  SYNTAX         Integer32
  MAX-ACCESS    read-create
  STATUS        current
  DESCRIPTION
    "This object contains the identifier of the protection type related to 
     opticsIMProtectionEqptPositionMain and opticsIMProtectionEqptPositionSpare 
     requested by the managing systems. 
     The identifier must be included in one of the entries of the 
     opticsIMAllowedProtectionTypesTable associated to the equipmentExpected 
     for the opticsIMProtectionEqptPositionMain and 
     opticsIMProtectionEqptPositionSpare.
     As a side effect of setting this object, the agent must set the
     opticsIMProtectionType object with the string associated to this 
     identifier (see opticsIMAllowedprotectionTypesTable)."
::= { opticsIMProtectionConfigurationEntry 6 }

--
opticsIMAllowedProtectionTypesTable OBJECT-TYPE
  SYNTAX SEQUENCE OF  OpticsIMAllowedProtectionTypesEntry
  MAX-ACCESS                    not-accessible
  STATUS                              current
  DESCRIPTION
    "This table contains, for each equipment type allowed in the NE, the 
     allowed protection types."
::= { opticsIMNeConfiguration 13 }

opticsIMAllowedProtectionTypesEntry OBJECT-TYPE
  SYNTAX                   OpticsIMAllowedProtectionTypesEntry
  MAX-ACCESS          not-accessible
  STATUS                    current
  DESCRIPTION
    "An entry of the allowed protection type table. Each entry (row) 
     corresponds to an protection type allowed for the equipment type identified
     by the equipmentType object."
  INDEX   { equipmentType, allowedProtectionTypeId }
::= { opticsIMAllowedProtectionTypesTable 1 }

OpticsIMAllowedProtectionTypesEntry ::= SEQUENCE {
  equipmentType                     DisplayString,
  allowedProtectionTypeId            Integer32,
  allowedProtectionType              DisplayString
  }

equipmentType OBJECT-TYPE
  SYNTAX                      DisplayString
  MAX-ACCESS            not-accessible
  STATUS                      current
  DESCRIPTION
    " This object contains an equipment type allowed on the NE."
::= { opticsIMAllowedProtectionTypesEntry 1 }

allowedProtectionTypeId OBJECT-TYPE
  SYNTAX                      Integer32
  MAX-ACCESS            not-accessible
  STATUS                      current
  DESCRIPTION
    "This object contains the identifier of an protection type allowed for 
     the associated equipment type."
::= { opticsIMAllowedProtectionTypesEntry 2 }

allowedProtectionType OBJECT-TYPE
  SYNTAX                     DisplayString
  MAX-ACCESS            read-only
  STATUS                      current
  DESCRIPTION
    "This object identifies the protection type (string) associated to the 
     allowedProtectionTypeId."
::= { opticsIMAllowedProtectionTypesEntry 3 }

-- TopologyGroup

opticsIMTopologyGroup OBJECT-TYPE
  SYNTAX   Integer32
  MAX-ACCESS                    read-write
  STATUS                              current
  DESCRIPTION
    "This object identifies the group that the NE belong to. A Service could 
     be created on NEs belonging to the same group."
::= { opticsIMNeConfiguration 14 }

-- opticsIMIfQueueTable

opticsIMIfQueueTable OBJECT-TYPE
  SYNTAX SEQUENCE OF OpticsIMIfQueueEntry
  MAX-ACCESS not-accessible
  STATUS current
  DESCRIPTION 
    "This table contains objects for each Forwarding queue of a NE interface."
::= { tsdimSnmpNEMibObject 46 }

opticsIMIfQueueEntry OBJECT-TYPE
  SYNTAX OpticsIMIfQueueEntry
  MAX-ACCESS not-accessible
  STATUS current
  DESCRIPTION
    "An entry references a forwarding Queue on each NE interface"
  INDEX { ifIndex, opticsIMIfQueueNumber }
::= { opticsIMIfQueueTable 1 }

OpticsIMIfQueueEntry ::= SEQUENCE {
  opticsIMIfQueueNumber                 Integer32,
  opticsIMIfQueueType                   INTEGER,
  opticsIMIfQueueWeight                 Integer32,
  opticsIMIfQueueNominalBandwidth       Gauge32,
  opticsIMIfQueueAvailableBandwidth     Gauge32,
  opticsIMIfQueueSlopeHiAdminStatus     INTEGER,
  opticsIMIfQueueSlopeHiStartAverage    Integer32,
  opticsIMIfQueueSlopeHiMaxAverage      Integer32,
  opticsIMIfQueueSlopeHiMaxProbability  Integer32,
  opticsIMIfQueueSlopeLoAdminStatus     INTEGER,
  opticsIMIfQueueSlopeLoStartAverage    Integer32,
  opticsIMIfQueueSlopeLoMaxAverage      Integer32,
  opticsIMIfQueueSlopeLoMaxProbability  Integer32,
  opticsIMIfQueueSize                   Integer32, 
  opticsIMIfQueueDefaultSize            Integer32

  }

opticsIMIfQueueNumber OBJECT-TYPE
  SYNTAX      Integer32 
  MAX-ACCESS  not-accessible
  STATUS      current
  DESCRIPTION
    "The number of the forwarding queue within the forwarding queue set"
::= { opticsIMIfQueueEntry 1 }

opticsIMIfQueueType OBJECT-TYPE
  SYNTAX      INTEGER {
    strictpriority (1),
    weightedbandwidth (2)
    }
  MAX-ACCESS  read-write
  STATUS      current
  DESCRIPTION
    "The type of the forwarding queue"
::= { opticsIMIfQueueEntry 2 }

opticsIMIfQueueWeight OBJECT-TYPE
  SYNTAX      Integer32 
  MAX-ACCESS  read-write
  STATUS      current
  DESCRIPTION
    "The weight assigned to a weighted bandwidth forwarding queue; the returned 
     value is meaningful ONLY for a weighted bandwidth forwarding queue"
    ::= { opticsIMIfQueueEntry 3 }

opticsIMIfQueueNominalBandwidth OBJECT-TYPE
  SYNTAX      Gauge32
  MAX-ACCESS  read-only
  STATUS      current
  DESCRIPTION
  "This attribute reports (in kbit/sec):
     - bandwidth parameter as inferred from assigned weight (in case of an 
       egress weighted bandwidth Forwarding Queue);
     - Egress Link nominal bandwidth (in case of an egress strict priority 
       Forwarding Queue)"
::= { opticsIMIfQueueEntry 4 }

opticsIMIfQueueAvailableBandwidth OBJECT-TYPE
  SYNTAX      Gauge32
  MAX-ACCESS  read-only
  STATUS      current
  DESCRIPTION
    "This attribute reports (in kbit/sec):
     - Available bandwidth parameter  (in case of an egress weighted bandwidth 
       Forwarding Queue);
     - Egress Link Available bandwidth (in case of an egress strict priority 
       Forwarding Queue)"
::= { opticsIMIfQueueEntry 5 }

opticsIMIfQueueSlopeHiAdminStatus  OBJECT-TYPE
  SYNTAX  INTEGER {
    up   (1),
    down (2)
    }
  MAX-ACCESS  read-write
  STATUS      current
  DESCRIPTION
    "opticsIMIfQueueSlopeHiAdminStatus specifies the admin state for the Green 
     packets (high priority) WRED slope. If the 
     opticsIMIfQueueSlopeHiAdminStatus is set to 'down', the WRED slope is 
     inactive. Default value is down"
::= { opticsIMIfQueueEntry 6 }

opticsIMIfQueueSlopeHiStartAverage  OBJECT-TYPE
  SYNTAX      Integer32 
  MAX-ACCESS  read-write
  STATUS      current
  DESCRIPTION
   "The percentage (0..100) of the buffer utilized after which the drop 
    probability of Green packets starts to rise above 0. Default value is 70"
::= { opticsIMIfQueueEntry  7 }

opticsIMIfQueueSlopeHiMaxAverage  OBJECT-TYPE
  SYNTAX      Integer32  
  MAX-ACCESS  read-write
  STATUS      current
  DESCRIPTION
    "The percentage (0..100) of the buffer utilized after which the drop 
     probability of Green packets is 100 percent. This implies that all Green 
     packets beyond this point will be dropped.Default value is 90"
::= { opticsIMIfQueueEntry  8 }

opticsIMIfQueueSlopeHiMaxProbability  OBJECT-TYPE
  SYNTAX      Integer32  
  MAX-ACCESS  read-write
  STATUS      current
  DESCRIPTION
    "The drop probability (0..100) of Green packets increases steadily from 0 
     (at opticsIMIfQueueSlopeHiStartAverage) up to 
     opticsIMIfQueueSlopeHiMaxProbability (at the 
     opticsIMIfQueueSlopeHiMaxAverage).
     Default value is 80"
::= { opticsIMIfQueueEntry  9 }

opticsIMIfQueueSlopeLoAdminStatus  OBJECT-TYPE
  SYNTAX      INTEGER {
    up   (1),
    down (2)
  }
  MAX-ACCESS  read-write
  STATUS      current
  DESCRIPTION
    "opticsIMIfQueueSlopeLoAdminStatus specifies the admin state for the Yellow 
     packet (Low priority) WRED slope. If opticsIMIfQueueSlopeLoAdminStatus is 
     set to 'down', the WRED slope is inactive.Default value is down"
::= { opticsIMIfQueueEntry  10 }

opticsIMIfQueueSlopeLoStartAverage  OBJECT-TYPE
  SYNTAX      Integer32 
  MAX-ACCESS  read-write
  STATUS      current
  DESCRIPTION
    "The percentage (0..100) of the buffer utilized after which the drop 
     probability of Yellow packet starts to rise above 0. Default value is 50"
::= { opticsIMIfQueueEntry  11 }

opticsIMIfQueueSlopeLoMaxAverage  OBJECT-TYPE
  SYNTAX      Integer32 
  MAX-ACCESS  read-write
  STATUS      current
  DESCRIPTION
    "The percentage of the buffer utilized after which the drop probability of
     Yellow packets is 100 percent. This implies that all packets beyond this 
     point will be dropped. Default is 75"
    ::= { opticsIMIfQueueEntry  12 }

opticsIMIfQueueSlopeLoMaxProbability  OBJECT-TYPE
  SYNTAX      Integer32 
  MAX-ACCESS  read-write
  STATUS      current
  DESCRIPTION
    "The drop probability (0..100) of Yellow packets increases steadily from 0 
     (at opticsIMIfQueueSlopeLoStartAverage) up to 
     opticsIMIfQueueSlopeLoMaxProbability (at the 
     opticsIMIfQueueSlopeLoMaxAverage).Default is 80"
::= { opticsIMIfQueueEntry  13 }

opticsIMIfQueueSize  OBJECT-TYPE
  SYNTAX      Integer32
  MAX-ACCESS  read-write
  STATUS      current
  DESCRIPTION
    "This object is the buffer size of the queue in bytes as defined by managing system.    
    "
::= { opticsIMIfQueueEntry  14 }

opticsIMIfQueueDefaultSize  OBJECT-TYPE
  SYNTAX      Integer32
  MAX-ACCESS  read-only
  STATUS      current
  DESCRIPTION
    "This object reports to the managing system the default value for the buffer size of the queue as applied by the agent.    
    "
::= { opticsIMIfQueueEntry  15 }


-- opticsIMIfEgressFCMappingTable
opticsIMIfEgressFCMappingTable OBJECT-TYPE
  SYNTAX       SEQUENCE OF OpticsIMIfEgressFCMappingEntry
  MAX-ACCESS   not-accessible
  STATUS       current
  DESCRIPTION  "  "
::= { tsdimSnmpNEMibObject 47 }

opticsIMIfEgressFCMappingEntry OBJECT-TYPE
  SYNTAX       OpticsIMIfEgressFCMappingEntry
  MAX-ACCESS   not-accessible
  STATUS       current
  DESCRIPTION
    "This entry contains information about mappings of a particular forwarding 
     class (including BOTH Green and Yellow packets) to a forwarding queue"
  INDEX {ifIndex, opticsIMIfEgressFCNumber}
::= { opticsIMIfEgressFCMappingTable 1 }

OpticsIMIfEgressFCMappingEntry ::= SEQUENCE
{
  opticsIMIfEgressFCNumber      Integer32, 
  opticsIMIfEgressFCQueue       Integer32
}

opticsIMIfEgressFCNumber OBJECT-TYPE
  SYNTAX      Integer32 
  MAX-ACCESS  not-accessible
  STATUS      current
  DESCRIPTION
    "The number of the Forwarding Class: Forwarding Classes are numbered
     starting from 0 to 7 with increasing forwarding priority (Forwarding 
     Class 0 with lowest forwarding priority)"
::= { opticsIMIfEgressFCMappingEntry 1 }

opticsIMIfEgressFCQueue OBJECT-TYPE
  SYNTAX       Integer32
  MAX-ACCESS   read-write
  STATUS       current
  DESCRIPTION
    "the Forwarding queue to use for packets in this forwarding class: 
     Forwarding Queues are numbered starting from 0 to N (Forwarding Queue 0 
     with lowest priority queue)"
::= { opticsIMIfEgressFCMappingEntry 2 }

opticsIMNeSLAType OBJECT-TYPE
  SYNTAX      INTEGER {
    full (1),
    fractional (2)
  }
  MAX-ACCESS  read-write
  STATUS      current
  DESCRIPTION
    "opticsIMNeSLAType specifies 'on per NE basis' the type of ETS Traffic
     Descriptors to be applied on each board in 'multi-board NE' supporting 
     multi-board Link Aggregation Interface.
     In case of full opticsIMNeSLAType the same ETS Traffic Descriptor (for 
     an ETS InFlow over a Link Aggregation Interface) is applied with full 
     Traffic Descriptor Parameters(CIR,PIR) to each board supporting at least 
     one Aggregation Port inside Link Aggregation Interface.

     In case of fractional opticsIMNeSLAType different instances of ETS Traffic 
     Descriptor (for an ETS InFlow over a Link Aggregation Interface) are 
     applied with fractional Traffic Descriptor Parameters(CIR,PIR) to each 
     board supporting at least one Aggregation Port inside Link Aggregation 
     Interface. Default value is full"
::= { tsdimSnmpNEMibObject 48 }

opticsimLinkOAMLogMinInterval OBJECT-TYPE
   SYNTAX     INTEGER (1..60)
   MAX-ACCESS read-write
   STATUS     current
   DESCRIPTION
     "This parameter defines the granularity window (sec) for the
      logging of LinkOAM event in the dot3OamEventLogTable.
      If more events of the same type are to be logged in this
      table in the window specified by this object, only the
      first one shall be logged."
   ::= { tsdimSnmpNEMibObject 49 }

-- ----------------

opticsIMNeAlarmsTable OBJECT-TYPE
  SYNTAX SEQUENCE OF OpticsIMNeAlarmsEntry
  MAX-ACCESS not-accessible
  STATUS current
  DESCRIPTION
    "Table for management of the ASAP object related to NE-level alarms.
     This table always contains only 1 single entry, with index value 1."
::= { tsdimSnmpNEMibObject 52 }

opticsIMNeAlarmsEntry OBJECT-TYPE
  SYNTAX OpticsIMNeAlarmsEntry
  MAX-ACCESS not-accessible
  STATUS current
  DESCRIPTION
    "Entry of table opticsIMNeAlarmsTable."
  INDEX { opticsIMNeAlarmsNeIndex  }
::= { opticsIMNeAlarmsTable 1 }

OpticsIMNeAlarmsEntry ::= SEQUENCE {
  opticsIMNeAlarmsNeIndex     OpticsIMNeAlarmsNeIndex,
  opticsIMNeAlarmsAsapIndex   Integer32
}

opticsIMNeAlarmsNeIndex OBJECT-TYPE
  SYNTAX OpticsIMNeAlarmsNeIndex
  MAX-ACCESS not-accessible
  STATUS current
  DESCRIPTION
    "Unique index for opticsIMNeAlarmsEntry. Only value 1 will be used."
::= { opticsIMNeAlarmsEntry 1 }

opticsIMNeAlarmsAsapIndex OBJECT-TYPE
  SYNTAX Integer32
  MAX-ACCESS read-write
  STATUS current
  DESCRIPTION
    "This object contains the ASAP object associated to the NE."
::= { opticsIMNeAlarmsEntry 2 }

-- TSDnm76841

opticsIMCfmStatus OBJECT-TYPE
  SYNTAX INTEGER {
    cfmDisable    (0),
    cfmEnable     (1)
  }
  MAX-ACCESS read-write
  STATUS current
  DESCRIPTION
    "This object modifies the global enable status of CFM. The default 
       is cfmDisable (0). In addition, when the status is disable, the 
       first Maintenance Domain (MD) creation changes the status to
       enable, and when the status is enable, the last MD deletion 
       changes the status to disable."
::= { tsdimSnmpNEMibObject 53 }

-- end TSDnm76841

-- TSDnm77715

opticsIMNeFrameSizeMode OBJECT-TYPE
  SYNTAX      INTEGER {
    native (0),
    layer1 (1),
    layer2 (2) 
  }
  MAX-ACCESS  read-write
  STATUS      current
  DESCRIPTION
    "opticsIMNeFrameSizeMode specifies 'on per NE basis' the type of ingress 
     policer, egress shaper and Performance Monitoring counters to be applied 
     to all NE ports:
     - native:  Policer and Ingress Performance Monitoring counters are BOTH 
                based on NE-product specific value on Ingress Port Shaper and 
		Egress Performance Monitoring counters are BOTH based on 
		NE-product specific value on Egress Port
     - layer1:  Ingress Policer, Egress Shaper and Ingress/Egress Performance 
                Monitoring counters are based on Layer1 
     - layer2:  Ingress Policer, Egress Shaper and Ingress/Egress Performance 
                Monitoring counters are based on Layer2. 
     Default value is NE-product specific"
::= { tsdimSnmpNEMibObject 54 }

-- end TSDnm77715

-- TSDnm75465

opticsIMNeSyncEthEnable OBJECT-TYPE
  SYNTAX      TruthValue 
  MAX-ACCESS  read-write
  STATUS      current
  DESCRIPTION
    "opticsIMNeSyncEthEnable specifies 'on per NE basis'enabled/disabled
     Ethernet Sync.
     Default value is false (Free running mode)"

::= { tsdimSnmpNEMibObject 55 }

-- end TSDnm75465

-- Begin ONDnm09836 - P.Villa - V5.00.

opticsIMNeOverClockedModeEnable OBJECT-TYPE
  SYNTAX      TruthValue 
  MAX-ACCESS  read-write
  STATUS      current
  DESCRIPTION
    "opticsIMNeOverClockedModeEnable specifies 'on per NE basis'enabled/disabled
     OverClocked Mode
     Default value is false (No over-clocked mode)"

::= { tsdimSnmpNEMibObject 64 }

-- End ONDnm09836.

-- Begin ONDnm09842 - P.Villa - V5.00.
opticsIMNeAlarmAdmin OBJECT-TYPE
  SYNTAX      INTEGER {
   mon  (1),
   auto (2)
    
  } 
  MAX-ACCESS  read-write
  STATUS      current
  DESCRIPTION
    "opticsIMNeAlarmAdmin  specifies 'on per NE basis' Alarm Admin value. Default value is mon(1)"

::= { tsdimSnmpNEMibObject 65 }

-- end ONDnm09842.


opticsIMIfQueueWREDAdminStatus OBJECT-TYPE
  SYNTAX  INTEGER {
    up   (1),
    down (2)
    }
  MAX-ACCESS  read-write
  STATUS      current
  DESCRIPTION
    "opticsIMIfQueueWREDAdminStatus specifies the admin state for the WRED slope. If the 
     opticsIMIfQueueWREDAdminStatus is set to 'down', the WRED slope is 
     inactive. Default value is down"

::= { tsdimSnmpNEMibObject 66 }

opticsIMMaintenanceMode OBJECT-TYPE
  SYNTAX  INTEGER {
    enable   (1),
    disable (2)
    }
  MAX-ACCESS  read-write
  STATUS      current
  DESCRIPTION
    "opticsIMNEMaintenanceMode set to 'enable' means the NE is entering in a Maintenance mode."

::= { tsdimSnmpNEMibObject 67 }


-- opticsIMCommonAlarms

opticsIMAlarmLossOfSignalRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Loss Of Signal (LOS) defect raise."
::= { opticsIMCommonAlarms 1 }

opticsIMAlarmLossOfSignalClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Loss Of Signal (LOS) defect clear."
::= { opticsIMCommonAlarms 2 }

-- Loss Of Frame alarm
opticsIMAlarmLossOfFrameRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Loss Of Frame (LOF) defect raise."
::= { opticsIMCommonAlarms 3 }

opticsIMAlarmLossOfFrameClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the Loss Of Frame (LOF) defect clear."
::= { opticsIMCommonAlarms 4 }

-- AIS alarm
opticsIMAlarmAisRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType 
  }
  STATUS current
  DESCRIPTION
    "This notification reports the AIS defect raise."
::= { opticsIMCommonAlarms 5 }

opticsIMAlarmAisClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the AIS defect clear."
::= { opticsIMCommonAlarms 6 }

-- Transmitter Failure alarm

opticsIMAlarmTransmitterFailureRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Transmitter Failure (TF) defect raise."
::= { opticsIMCommonAlarms 7 }

opticsIMAlarmTransmitterFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Transmitter Failure (TF) defect clear."
::= { opticsIMCommonAlarms 8 }

-- Transmitter Degraded alarm

opticsIMAlarmTransmitterDegradedRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Transmitter Degraded (TD) defect raise."
::= { opticsIMCommonAlarms 9 }

opticsIMAlarmTransmitterDegradedClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Transmitter Degraded (TD) defect clear."
::= { opticsIMCommonAlarms 10 }

-- Remote Defect Indication alarm
opticsIMAlarmRemoteDefectIndicationRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the Remote Defect Indication (RDI) defect raise."
::= { opticsIMCommonAlarms 11 }

opticsIMAlarmRemoteDefectIndicationClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Remote Defect Indication (RDI) defect clear."
::= { opticsIMCommonAlarms 12 }

-- Cable LOS alarm

opticsIMAlarmCableLOSRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the Cable LOS defect raise."
::= { opticsIMCommonAlarms 13 }

opticsIMAlarmCableLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Cable LOS defect clear."
::= { opticsIMCommonAlarms 14 }

-- rxLOS alarm
opticsIMAlarmRxLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the rxLOS (LOS of the incoming signal for the 
     Rx subfunction) defect raise."
::= { opticsIMCommonAlarms 15 }

opticsIMAlarmRxLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the rxLOS (LOS of the incoming signal for the 
     Rx subfunction) defect clear."
::= { opticsIMCommonAlarms 16 }

-- rxFail alarm
opticsIMAlarmRxFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType 
  }
  STATUS current
  DESCRIPTION 
    "This notification reports the rxFail (a fail of the Rx subfunction) 
     defect raise."
::= { opticsIMCommonAlarms 17 }

opticsIMAlarmRxFailClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the rxFail (a fail of the  Rx subfunction) 
     defect clear."
::= { opticsIMCommonAlarms 18 }

-- demLOS alarm
opticsIMAlarmDemLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the demLOS (LOS of the incoming signal for the 
     demodulation subfunction) defect raise."
::= { opticsIMCommonAlarms 19 }

opticsIMAlarmDemLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the demLOS (LOS of the incoming signal for the 
     demodulation subfunction) defect clear."
::= { opticsIMCommonAlarms 20 }

-- demFail alarm
opticsIMAlarmDemFailRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the demFail (a fail of the demodulation 
     subfunction) defect raise."
::= { opticsIMCommonAlarms 21 }

opticsIMAlarmDemFailClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the DemFail (a fail of the demodulation 
     subfunction) defect clear."
::= { opticsIMCommonAlarms 22 }

-- modLOS alarm

opticsIMAlarmModLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the modLOS (LOS of the incoming signal for the 
     modulation subfunction) defect raise."
::= { opticsIMCommonAlarms 23 }

opticsIMAlarmModLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the modLOS (LOS of the incoming signal for the modulation subfunction) defect clear."
::= { opticsIMCommonAlarms 24 }

-- modFail alarm
opticsIMAlarmModFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the modFail (a fail of the modulation 
     subfunction) defect raise."
::= { opticsIMCommonAlarms 25 }

opticsIMAlarmModFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the modFail (a fail of the modulation 
     subfunction) defect clear."
::= { opticsIMCommonAlarms 26 }

-- txLOS alarm

opticsIMAlarmTxLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the txLOS (LOS of the incoming signal for the 
     Tx subfunction) defect raise."
::= { opticsIMCommonAlarms 27 }

opticsIMAlarmTxLOSClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the txLOS (LOS of the incoming signal for the 
     Tx subfunction) defect clear."
::= { opticsIMCommonAlarms 28 }

-- txFail alarm

opticsIMAlarmTxFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the txFail (a fail of the Tx subfunction) defect
     raise."
::= { opticsIMCommonAlarms 29 }

opticsIMAlarmTxFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the txFail (a fail of the Tx subfunction) defect
     clear."
::= { opticsIMCommonAlarms 30 }

-- threshold crossing alarm
opticsIMAlarmTCARaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Threshold Crossing Alarm defect raise."
::= { opticsIMCommonAlarms 31 }

opticsIMAlarmTCAClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the Threshold Crossing Alarm defect clear."
::= { opticsIMCommonAlarms 32 }

-- unavailable time alarm
opticsIMAlarmUnavailableTimeRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the Unavailable Time defect raise."
::= { opticsIMCommonAlarms 33 }

opticsIMAlarmUnavailableTimeClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Unavailable Time defect clear."
::= { opticsIMCommonAlarms 34 }

-- Trail Signal Fail alarm
opticsIMAlarmTsfRaise NOTIFICATION-TYPE
  OBJECTS {
    tsdimEventObjectClassIdentifier,
    tsdimEventObjectInstanceIdentifier,
    tsdimEventNotificationId,
    tsdimEventTime,
    tsdimAlarmSeverity,        
    tsdimAlarmSpecProblem,
    opticsIMAdditionalText,
    opticsIMAlarmType
  }
  STATUS current    
  DESCRIPTION
    "This notification reports the Trail Signal Fail TSF) alarm.
     It does not apply to ATM interfaces where the tsdimAlarmTsfRaise 
     notification is used."
::= { opticsIMCommonAlarms 35 }

opticsIMAlarmTsfClear NOTIFICATION-TYPE
  OBJECTS {
    tsdimEventObjectClassIdentifier,
    tsdimEventObjectInstanceIdentifier,
    tsdimEventNotificationId,        
    tsdimEventTime,
    tsdimAlarmSeverity,        
    tsdimAlarmSpecProblem,
    opticsIMAdditionalText,
    opticsIMAlarmType
  }
  STATUS current
  DESCRIPTION
    "This notification reports the Trail Signal Fail (TSF) alarm clear.
     It does not apply to ATM interfaces where the tsdimAlarmTsfClear 
     notification is used."
::= { opticsIMCommonAlarms 36 }

-- Payload Mismatch alarm
opticsIMAlarmPlmRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Payload Mismatch (PLM) alarm.
     It does not apply to ATM interfaces where the tsdimAlarmPlmRaise 
     notification is used."
::= { opticsIMCommonAlarms 37 }

opticsIMAlarmPlmClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Payload Mismatch (PLM) alarm clear.
     It does not apply to ATM interfaces where the tsdimAlarmPlmClear 
     notification is used."
::= { opticsIMCommonAlarms 38 }

-- Underline Resource Unavailable alarm
opticsIMAlarmUruRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Underline Resource Unavailable (URU) defect
     raise."
::= { opticsIMCommonAlarms 39 }

opticsIMAlarmUruClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Underline Resource Unavailable (URU) defect
     clear."
::= { opticsIMCommonAlarms 40 }

-- LAPD Fail alarm
opticsIMAlarmLAPDFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the LAPD Fail defect raise."
::= { opticsIMCommonAlarms 41 }

opticsIMAlarmLAPDFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType }
  STATUS current
  DESCRIPTION 
    "This notification reports the LAPD Fail defect clear."
::= { opticsIMCommonAlarms 42}

-- GFP Type Mismatch alarm
opticsimGfpAlarmGtmRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the GFP Type Mismatch (GTM) alarm."
::= { opticsIMCommonAlarms 43 }

opticsimGfpAlarmGtmClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the GFP Type Mismatch (GTM) alarm clear."
::= { opticsIMCommonAlarms 44 }

-- Loss of DACM alarm
opticsimDAAlarmDACMRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Loss of DACM alarm."
::= { opticsIMCommonAlarms 45 }

opticsimDAAlarmDACMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Loss of DACM alarm clear."
::= { opticsIMCommonAlarms 46 }


-- Loss of Alignment alarm

opticsIMAlarmLossOfAlignmentRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the Loss of Alignment defect raise."
::= { opticsIMCommonAlarms 47 }

opticsIMAlarmLossOfAlignmentClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Loss of Alignment defect clear."
::= { opticsIMCommonAlarms 48}


-- Point to Point IP Fail alarm
opticsIMAlarmPPPFailRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Point to Point IP Fail defect raise."
::= { opticsIMCommonAlarms 49 }

opticsIMAlarmPPPFailClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the Point to Point IP Fail defect clear."
::= { opticsIMCommonAlarms 50}

-- Remote NE Failure alarm
opticsIMAlarmRemoteNEFailureRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Remote NE Failure defect raise."
::= { opticsIMCommonAlarms 51 }

opticsIMAlarmRemoteNEFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Remote NE Failure defect clear."
::= { opticsIMCommonAlarms 52}

-- SDH Concatention Degrade
opticsimSdhConcDegradeRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports that at least one active VC in a virtual or 
    packet concatenated group is not working and therefore the 
    opticsIMSdhIfCurrSpeed is lower than the nominal opticsIMSdhIfSpeed."
::= { opticsIMCommonAlarms 53 }

opticsimSdhConcDegradeClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the all the active VCs in a virtual or packet 
     concatenated group are working."
::= { opticsIMCommonAlarms 54}

opticsimClientSignalFailRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "Client Signal Fail raise."
::= { opticsIMCommonAlarms 55}

opticsimClientSignalFailClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "Client Signal Fail clear."
::= { opticsIMCommonAlarms 56}

opticsIMAlarmLossOfPointerRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Loss of Pointer defect raise."
::= { opticsIMCommonAlarms 57}

opticsIMAlarmLossOfPointerClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Loss of Pointer defect clear."
::= { opticsIMCommonAlarms 58}

opticsIMAlarmLossOfMultiframeRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
   }
   STATUS current
   DESCRIPTION 
     "This notification reports the Loss of Multiframe defect raise."
::= { opticsIMCommonAlarms 59}

opticsIMAlarmLossOfMultiframeClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Loss of Multiframe defect clear."
::= { opticsIMCommonAlarms 60}

opticsIMAlarmSequenceMismatchRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Sequence mismatch defect raise."
::= { opticsIMCommonAlarms 61}
opticsIMAlarmSequenceMismatchClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the Sequence mismatch defect clear."
::= { opticsIMCommonAlarms 62}

opticsIMAlarmServerSignalFailRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Server Signal Fail raise."
::= { opticsIMCommonAlarms 63}

opticsIMAlarmServerSignalFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Server Signal Fail clear."
::= { opticsIMCommonAlarms 64}

opticsIMAlarmUnequippedRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the VC-n unequipped defect raise."
::= { opticsIMCommonAlarms 65}

opticsIMAlarmUnequippedClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the VC-n unequipped defect clear."
::= { opticsIMCommonAlarms 66}

opticsIMAlarmExstensionHeaderMismatchRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the Exstension Header Mismatch (EXM) defect 
     raise."
::= { opticsIMCommonAlarms 67 }

opticsIMAlarmExstensionHeaderMismatchClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the Exstension Header Mismatch (EXM) defect 
     clear."
::= { opticsIMCommonAlarms 68 }

opticsIMAlarmUserPayloadMismatchRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the User Payload Mismatch (UPM) defect raise."
::= { opticsIMCommonAlarms 69 }

opticsIMAlarmUserPayloadMismatchClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the User Payload Mismatch (UPM) defect clear."
::= { opticsIMCommonAlarms 70 }

opticsIMAlarmDegradeRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports Degraded defect raise."
::= { opticsIMCommonAlarms 71 }

opticsIMAlarmDegradeClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports Degraded defect clear."
::= { opticsIMCommonAlarms 72 }

opticsimAlarmInputPowerDegradeRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports input power Degraded defect raise."
::= { opticsIMCommonAlarms 73 }

opticsimAlarmInputPowerDegradeClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports input power Degraded defect clear."
::= { opticsIMCommonAlarms 74 }

opticsimAlarmMisconnectionRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports Misconnection of CESoETH frames defect raise."
::= { opticsIMCommonAlarms 75 }

opticsimAlarmMisconnectionClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports Misconnection of CESoETH frames defect clear."
::= { opticsIMCommonAlarms 76 }

opticsimAlarmLateFramesRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports Late arriving CESoETH Frames defect raise."
::= { opticsIMCommonAlarms 77 }

opticsimAlarmLateFramesClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports Late arriving CESoETH Frames defect clear."
::= { opticsIMCommonAlarms 78 }

opticsimAlarmMalformedFramesRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType }
  STATUS current
  DESCRIPTION 
    "This notification reports Malformed Frames defect raise."
::= { opticsIMCommonAlarms 79 }

opticsimAlarmMalformedFramesClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports Malformed Frames defect clear."
::= { opticsIMCommonAlarms 80 }

opticsimAlarmJitterBufferOverrunRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Jitter Buffer Overrun defect raise."
::= { opticsIMCommonAlarms 81 }

opticsimAlarmJitterBufferOverrunClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    " This notification reports the Jitter Buffer Overrun defect clear."
::= { opticsIMCommonAlarms 82 }

opticsimAlarmJitterBufferUnderrunRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Jitter Buffer Underrun defect raise."
::= { opticsIMCommonAlarms 83 }

opticsimAlarmJitterBufferUnderrunClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Jitter Buffer Underrun defect clear."
::= { opticsIMCommonAlarms 84 }

opticsimAlarmServerSignalIngrFailRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Server Signal Fail on ingressing raise."
::= { opticsIMCommonAlarms 85 }

opticsimAlarmServerSignalIngrFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Server Signal Fail on ingressing clear."
::= { opticsIMCommonAlarms 86 }

opticsimAlarmServerSignalEgreFailRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Server Signal Fail on egressing raise."
::= { opticsIMCommonAlarms 87 }

opticsimAlarmServerSignalEgreFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Server Signal Fail on egressing clear."
::= { opticsIMCommonAlarms 88 }

opticsimAlarmTrafficDisableRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Traffic Disable raise."
::= { opticsIMCommonAlarms 89 }

opticsimAlarmTrafficDisableClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Traffic disable clear."
::= { opticsIMCommonAlarms 90 }

--- Ethernet OAM alarms Begin
opticsimAlarmEthOAMLossOfContinuityRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Loss Of 
     Continuity raise."
::= { opticsIMCommonAlarms 91 }

opticsimAlarmEthOAMLossOfContinuityClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Loss Of 
     Continuity clear."
::= { opticsIMCommonAlarms 92 }

opticsimAlarmEthOAMMisMergeConditionRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) MisMerge 
     Condition raise."
::= { opticsIMCommonAlarms 93 }

opticsimAlarmEthOAMMisMergeConditionClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) MisMerge 
     Condition clear."
::= { opticsIMCommonAlarms 94 }

opticsimAlarmEthOAMUnexpectedMepIdRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) UnexpectedMepId 
     raise."
::= { opticsIMCommonAlarms 95 }

opticsimAlarmEthOAMUnexpectedMepIdClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) UnexpectedMepId 
    Clear."
::= { opticsIMCommonAlarms 96 }

opticsimAlarmEthOAMUnexpectedPeriodRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Unexpected 
     Period raise."
::= { opticsIMCommonAlarms 97 }

opticsimAlarmEthOAMUnexpectedPeriodClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Unexpected
     Period Clear."
::= { opticsIMCommonAlarms 98 }

opticsimAlarmEthOAMUnexpectedLevelRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Unexpected
     Level raise."
::= { opticsIMCommonAlarms 99 }

opticsimAlarmEthOAMUnexpectedLevelClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Unexpected Level
     clear."
::= { opticsIMCommonAlarms 100 }

opticsimAlarmEthOAMRDIRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Remote Defect
     Indication raise."
::= { opticsIMCommonAlarms 101 }

opticsimAlarmEthOAMRDIClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) Remote Defect
     Indication clear."
::= { opticsIMCommonAlarms 102 }

--- Ethernet OAM alarms End

-- synchronizationFail alarm
opticsimAlarmSynchronizationSignalFailRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the synchronization signal fail raise."
::= { opticsIMCommonAlarms 103 }

opticsimAlarmSynchronizationSignalFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the synchronization signal fail clear."
::= { opticsIMCommonAlarms 104 }

-- License mismatch alarm
opticsIMMemoryCardForbiddenToUseRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Memory card forbidden to use alarm raise."
::= { opticsIMCommonAlarms 105 }

opticsIMMemoryCardForbiddenToUseClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Memory card forbidden to use alarm clear."
::= { opticsIMCommonAlarms 106 }

opticsIMAlarmLinkOdncRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the unsuccessful completion of Link OAM
     Discovery protocol."
::= { opticsIMCommonAlarms 107 }

opticsIMAlarmLinkOdncClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the ODNC defect clear."
::= { opticsIMCommonAlarms 108 }

opticsIMAlarmLinkCleRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports that at least one Critical Link Event flag is
     present in the received OAMPDUs."
::= { opticsIMCommonAlarms 109 }

opticsIMAlarmLinkCleClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the CL Event defect clear."
::= { opticsIMCommonAlarms 110 }

opticsIMAlarmLinkSiRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports an inconsistency of states between the two peer
     DTEs"
::= { opticsIMCommonAlarms 111 }

opticsIMAlarmLinkSiClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the SI defect clear."
::= { opticsIMCommonAlarms 112 }

opticsimAlarmEthOAMUNPrRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports 'A MEP receives a CCM frame with an invalid
     Priority, but a valid MEG and MEP values' raise."
::= { opticsIMCommonAlarms 113 }

opticsimAlarmEthOAMUNPrClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports 'A MEP receives a CCM frame with an invalid
     Priority, but a valid MEG and MEP values' clear."
::= { opticsIMCommonAlarms 114 }

opticsimAlarmClockFailureRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the failure of the clock raise."
::= { opticsIMCommonAlarms 115 }

opticsimAlarmClockFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the the failure of the clock clear."
::= { opticsIMCommonAlarms 116 }

opticsimAlarmEthSignalDegradedRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the signal degrade on the Ethernet link raise."
::= { opticsIMCommonAlarms 117 }

opticsimAlarmEthSignalDegradeClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the signal degrade on the Ethernet link clear."
::= { opticsIMCommonAlarms 118 }

opticsimAlarmEthPNACRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports that the 'ethernet port-based authentication is 
     failed' is raised."
::= { opticsIMCommonAlarms 119 }
 
opticsimAlarmEthPNACClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports that 'ethernet port-based authentication is
     failed' is cleared."
::= { opticsIMCommonAlarms 120 }

opticsimAlarmAutomaticEthShutdownRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the 'Ethernet port shutdown' due not to local
     problems (on Ethernet port) but due to some problems on the associated 
     interface on NE' defect raise."
::= { opticsIMCommonAlarms 121 }
 
opticsimAlarmAutomaticEthShutdownClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the 'Ethernet port shutdown' due not to local
     problems (on Ethernet port) but due to some problems on the associated 
     interface on NE' defect clear."
::= { opticsIMCommonAlarms 122 }

opticsimAlarmEthFOPCMRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame from the working
     transport entity for ethernet 1:1 EVC protection group' is raise."
::= { opticsIMCommonAlarms 123 }
 
opticsimAlarmEthFOPCMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
   "This notification for 'Reception of an APS frame from the working
    transport entity for ethernet 1:1 EVC protection group' is clear"
::= { opticsIMCommonAlarms 124 }

opticsimAlarmEthFOPPMRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible -B-
     bit value' is raise."
::= { opticsIMCommonAlarms 125 }
 
opticsimAlarmEthFOPPMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible -B-
     bit value' is clear"
::= { opticsIMCommonAlarms 126 }    

opticsimAlarmEthFOPNRRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible
     -Requested Signal- value' is raise."
::= { opticsIMCommonAlarms 127 }

opticsimAlarmEthFOPNRClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible
     -Requested Signal- value' is clear"
::= { opticsIMCommonAlarms 128 }

opticsimAlarmEthFOPAMRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible -A-
     bit value' is raise."
::= { opticsIMCommonAlarms 129 }
 
opticsimAlarmEthFOPAMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible -A-
     bit value' is clear"
::= { opticsIMCommonAlarms 130 }   

opticsimAlarmEthFOPDMRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible -D-
     bit value' is raise."
::= { opticsIMCommonAlarms 131 }
 
opticsimAlarmEthFOPDMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Reception of an APS frame with incompatible -D-
     bit value' is clear"
::= { opticsIMCommonAlarms 132 }  

opticsimAlarmEthNOSYNCRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Loss Of synchronisation for ethernet port' is raise"
::= { opticsIMCommonAlarms 133 }

opticsimAlarmEthNOSYNClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Loss Of synchronisation for ethernet port' is clear"
::= { opticsIMCommonAlarms 134 }    

opticsimAlarmEthANMRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Auto-Negotiation_Mismatch' is raise."
::= { opticsIMCommonAlarms 135 }
 
opticsimAlarmEthANMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Auto-Negotiation_Mismatcht' is clear"
::= { opticsIMCommonAlarms 136 }

opticsimAlarmHldOverRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'The system clock is in the holdover or
     free-running mode' is raise."
::= { opticsIMCommonAlarms 137 }
 
opticsimAlarmHldOverClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'The system clock is in the holdover or
     free-running mode' is clear"
::= { opticsIMCommonAlarms 138 }  

opticsimTLURaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Timing Link Unequiped' is raise."
::= { opticsIMCommonAlarms 139 }
 
opticsimTLUClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Timing Link Unequiped' is clear"
::= { opticsIMCommonAlarms 140 }

opticsimAlarmPDHTLCRRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Total loss capacity in receive direction' is raise"
::= { opticsIMCommonAlarms 141 }
 
opticsimAlarmPDHTLCRClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Total loss capacity in receive direction' is clear"
::= { opticsIMCommonAlarms 142 }   

opticsimAlarmPDHTLCTRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Total loss capacity in transmission direction' is
     raise."
::= { opticsIMCommonAlarms 143 }
 
opticsimAlarmPDHTLCTClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Total loss capacity in transmission direction' is
     clear"
::= { opticsIMCommonAlarms 144 }         

opticsimAlarmPDHPLCTRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Patial loss capacity in transmission direction' is
     raise."
::= { opticsIMCommonAlarms 145 }
 
opticsimAlarmPDHPLCTClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Patial loss capacity in transmission direction' is clear"
::= { opticsIMCommonAlarms 146 }    

opticsimAlarmPDHPLCRRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Patial loss capacity in receive direction' is raise"
::= { opticsIMCommonAlarms 147 }
 
opticsimAlarmPDHPLCRClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Patial loss capacity in receive direction' is clear"
::= { opticsIMCommonAlarms 148 }  

opticsimAlarmPDHMNDRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Member not deskewable fault cause' is raise"
::= { opticsIMCommonAlarms 149 }
 
opticsimAlarmPDHMNDClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification for 'Member not deskewable fault cause' is clear"
::= { opticsIMCommonAlarms 150 }

opticsIMRetimingBufferOverflowRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the 'Ethernet port shutdown' due not to local
     problems (on Ethernet port) but due to some problems on the associated
     interface on NE' defect raise."
::= { opticsIMCommonAlarms 151 }
 
opticsIMRetimingBufferOverflowClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the 'Ethernet port shutdown' due not to local
     problems (on Ethernet port) but due to some problems on the associated 
     interface on NE' defect clear."
::= { opticsIMCommonAlarms 152 }

opticsimAlarmFailureOfProtocolProvisioningMismatchRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Failure of protocol Provisioning Mismatch
     event raise"
::= { opticsIMCommonAlarms 153 }

opticsimAlarmFailureOfProtocolProvisioningMismatchClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Failure of protocol Provisioning Mismatch
     event clear"
::= { opticsIMCommonAlarms 154 }

opticsimAlarmFailureOfProtocolTimeOutRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Failure of protocol TimeOut event raise"
::= { opticsIMCommonAlarms 155 }

opticsimAlarmFailureOfProtocolTimeOutClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Failure of protocol TimeOut event clear"
::= { opticsIMCommonAlarms 156 }

opticsimAlarmLoopingFrameEventRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the looping frame event raise"
::= { opticsIMCommonAlarms 157 }
 
opticsimAlarmLoopingFrameEventClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the looping frame event clear "
::= { opticsIMCommonAlarms 158 }

opticsimAlarmEthOAMMIPOverflowEventRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the MIP OverFlow event raise"
::= { opticsIMCommonAlarms 159 }
 
opticsimAlarmEthOAMMIPOverflowEventClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the MIP OverFlow event clear "
::= { opticsIMCommonAlarms 160 }

opticsimAlarmMcastTableOverflowEventRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Multicast table OverFlow event raise"
::= { opticsIMCommonAlarms 161 }
 
opticsimAlarmMcastTableOverflowEventClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Multicast table OverFlow event clear"
::= { opticsIMCommonAlarms 162 }

opticsimAlarmEthOAMVSFRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the VSF defect raise."
::= { opticsIMCommonAlarms 163 }
 
opticsimAlarmEthOAMVSFClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the VSF defect clear."
::= { opticsIMCommonAlarms 164 }

opticsIMAlarmExSERRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports an excessive rate of symbol errors on the line.
     In case of 10GE interfaces it reports an excessive rate of invalid blocks.
     The threshold rate is configurable as maximum number of symbol errors/
     invalid blocks in one second using the opticsIMlinkEnhSymbErrThr object 
     in opticsIMlinkEnhTable."
::= { opticsIMCommonAlarms 165 }

opticsIMAlarmExSERClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports an excessive symbol error rate alarm clear."
::= { opticsIMCommonAlarms 166 }

opticsIMAlarmLossOfCESoETHFrameRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the loss of CES Frame (LCF) defect raise"
::= { opticsIMCommonAlarms 167 }

opticsIMAlarmLossOfCESoETHFrameClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the loss of CES Frame (LCF) defect clear"
::= { opticsIMCommonAlarms 168 }

opticsimAlarmLossOfProtectionRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the loss of protection defect raise."
::= { opticsIMCommonAlarms 169 }

opticsimAlarmLossOfProtectionClear NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the loss of protection defect clear."
::= { opticsIMCommonAlarms 170 }

opticsIMAlarmAisTxRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
      DESCRIPTION
          "This notification reports the AIS in Tx direction defect raise."
::= { opticsIMCommonAlarms 171 }

opticsIMAlarmAisTxClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the AIS in Tx direction defect clear."
::= { opticsIMCommonAlarms 172 }

opticsIMAlarmAisRxRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the AIS in Rx direction defect raise."
::= { opticsIMCommonAlarms 173 }

opticsIMAlarmAisRxClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the AIS in Rx direction defect clear."
::= { opticsIMCommonAlarms 174 }

-- Underline Resource Degraded alarm

opticsIMAlarmUrdRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Underline Resource Degraded (URD) defect
     raise."
::= { opticsIMCommonAlarms 175 }

opticsIMAlarmUrdClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Underline Resource Degraded (URD) defect
     clear."
::= { opticsIMCommonAlarms 176 }

-- Underline Resource Unavailable Service alarm

opticsIMAlarmUrusRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Underline Resource Unavailable Service (URUS) defect
     raise."
::= { opticsIMCommonAlarms 177 }

opticsIMAlarmUrusClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Underline Resource Unavailable Service (URUS) defect
     clear."
::= { opticsIMCommonAlarms 178 }


opticsIMAlarmLossOfESMCRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Loss of Ethernet Synchronisation Messaging Channel defect 
     raise."
::= { opticsIMCommonAlarms 179 }

opticsIMAlarmLossOfESMCClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Loss of Ethernet Synchronisation Messaging Channel defect 
     clear."
::= { opticsIMCommonAlarms 180 }

-- CES Stray Packets Alarm

opticsIMAlarmStraypacketsRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Stray Packets defect raise."
::= { opticsIMCommonAlarms 181 }

opticsIMAlarmStraypacketsClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Stray Packets defect clear."
::= { opticsIMCommonAlarms 182 }

-- CES Excessive packet loss rate Alarm

opticsIMAlarmExcessivepacketLossRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Excessive Packet Loss defect raise."
::= { opticsIMCommonAlarms 183 }

opticsIMAlarmExcessivepacketLossClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Excessive Packet Loss Rate defect clear."
::= { opticsIMCommonAlarms 184 }

-- CES Remote packet loss rate Alarm

opticsIMAlarmRemotepacketlossRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports the Remote Packet Loss defect raise."
::= { opticsIMCommonAlarms 185 }

opticsIMAlarmRemotepacketlossClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Remote Packet Loss defect clear."
::= { opticsIMCommonAlarms 186 }

-- TSDnm81032

opticsIMAlarm1PpsTodLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if 1PPS pulse can't be detected within 3s time if the
1PPS/TOD interface is enabled.."
::= { opticsIMCommonAlarms 187 }

opticsIMAlarm1PpsTodLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if 1PPS signal can be detected within 1s time for
consecutive 3s timeline."
::= { opticsIMCommonAlarms 188 }

-- 1Pps ToD DEG alarm

opticsIMAlarm1PpsToDDEGRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if  1PPS pulse can be received within 1s 
    time (not 1PPS/TOD LOS) but the operational status of 1PPS is degraded and
the 1PPS/TOD interface is enabled."
::= { opticsIMCommonAlarms 189 }

opticsIMAlarm1PpsToDDEGClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if  1PPS pulse can be received within 1s time (not
     1PPS/TOD LOS) and the operational status of 1PPS/ToD is normal."
::= { opticsIMCommonAlarms 190 }

--Ptp Loss Of Lock Alarm
opticsIMAlarmPtpLossOfLockRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if PTP recovered Clock state is NOT in LOCKED state
     and the PTP port is enabled."
::= { opticsIMCommonAlarms 191 }

opticsIMAlarmPtpLossOfLockClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if PTP recovered Clock state is in LOCKED state."
::= { opticsIMCommonAlarms 192 }

-- Ptp Faulty Alarm
opticsIMAlarmPtpFaultyRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if PTP port is in Faulty and the PTP port is
     enabled."
::= { opticsIMCommonAlarms 193 }

opticsIMAlarmPtpFaultyClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if PTP recovered Clock state is NOT in Faulty
     state."
::= { opticsIMCommonAlarms 194 }


-- end of TSDnm81032

-- TSDnm83474

-- CES TDM invalid alarm

opticsIMAlarmInvalidTdmDataRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "This notification reports that the 'L' bit is set in SAToP Control Word, 
     it indicate that TDM data carried in the payload is invalid due to an 
     attachment circuit fault."
::= { opticsIMCommonAlarms 195 }

opticsIMAlarmInvalidTdmDataClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports that the 'L' bit is cleared in SAToP Control Word:."
::= { opticsIMCommonAlarms 196 }

-- end of TSDnm83474

-- begin of TSDnm85343

opticsIMAlarmIncompatibleProtectionRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the incompatibility between equipment for protection scope."
::= { opticsIMCommonAlarms 197 }

opticsIMAlarmIncompatibleProtectionClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the incompatibility between equipment for protection scope."
::= { opticsIMCommonAlarms 198}

-- end of TSDnm85343

-- begin of TSDnm91916

opticsIMAlarmBandwidthDegradeForProtectionSwitchRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the bandwidth degrade in case of protection switch."
::= { opticsIMCommonAlarms 199 }

opticsIMAlarmBandwidthDegradeForProtectionSwitchClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the bandwidth degrade in case of protection switch."
::= { opticsIMCommonAlarms 200}

-- end of TSDnm91916

-- 

opticsIMAlarmDuplicatedAddressDetectedRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the detection of an IP address duplication."
::= { opticsIMCommonAlarms 201 }

opticsIMAlarmDuplicatedAddressDetectedClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the detection of an IP address duplication."
::= { opticsIMCommonAlarms 202}

--

-- begin of OPTnm24314
  
 opticsIMAlarmLoopbackPresenceRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the loopback alarm presence."
::= { opticsIMCommonAlarms 203 }

opticsIMAlarmLoopbackPresenceClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the loopback alarm presence."
::= { opticsIMCommonAlarms 204}

-- end of OPTnm24314

-- begin of OPTnm26385
  
 opticsIMAlarmServiceSelectiveDropRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the service selective drop ."
::= { opticsIMCommonAlarms 205 }

opticsIMAlarmServiceSelectiveDropClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the service selective drop."
::= { opticsIMCommonAlarms 206}

-- end of OPTnm26385

-- begin of OPTnm26463
  
 opticsimAlarmlnkaggExBandwidthDegradeRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the LAG Excessive Bandwidth Degrade alarm presence."
::= { opticsIMCommonAlarms 207 }

opticsimAlarmlnkaggExBandwidthDegradeClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the LAG Excessive Bandwidth Degrade alarm presence."
::= { opticsIMCommonAlarms 208}

-- end of OPTnm26463


-- Begin of OPTnm26601: Remote Fault Indication alarm

opticsIMAlarmRemoteFaultIndicationRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION
    "This notification reports the Remote Fault Indication (RFI) defect raise."
::= { opticsIMCommonAlarms 209 }

opticsIMAlarmRemoteFaultIndicationClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the Remote Fault Indication (RFI) defect clear."
::= { opticsIMCommonAlarms 210 }

-- end of OPTnm26601

-- begin OPTnm26383 
-- CMCC Sync. OAM Alarm
opticsIMAlarm1588AnnouncePktLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if the 1588 Announce packet loss is detected, the
default detect interval is 3 packets."
::= { opticsIMCommonAlarms 211 }

opticsIMAlarm1588AnnouncePktLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if the 1588 Announce packet loss is not detected."
::= { opticsIMCommonAlarms 212 }  

opticsIMAlarm1588SyncPktLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if the 1588 sync packet loss is detected, the default detect interval is 3 packets."
::= { opticsIMCommonAlarms 213 }

opticsIMAlarm1588SyncPktLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if the 1588 sync packet loss is not detected."
::= { opticsIMCommonAlarms 214 }
 
opticsIMAlarm1588DelayRespPktLOSRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if the 1588 Delay_resp packet is not received, the default detect interval is 3 packets."
::= { opticsIMCommonAlarms 215 }

opticsIMAlarm1588DelayRespPktLOSClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if the 1588 Delay_resp packet is received."
::= { opticsIMCommonAlarms 216 }

opticsIMAlarm1588PTPClockclassDEGRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm is raised if PTP clockclass is smaller than the value of the specific threshold,and the value of 'stepsRemoved' for PTP reference source is '0', the default
threshold value is 6."
::= { opticsIMCommonAlarms 217 }

opticsIMAlarm1588PTPClockclassDEGClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm is cleared if PTP clockclass is bigger than the value of the specific threshold,or the value of 'stepsRemoved' for PTP reference source is not '0', the default
threshold value is 6."
::= { opticsIMCommonAlarms 218 }

opticsIMAlarmESMCPktLosRaise NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION 
    "The alarm shall be raised if the ESMC packet is lost."
::= { opticsIMCommonAlarms 219 }

opticsIMAlarmESMCPktLosClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "The alarm shall be cleared if the ESMC packet is received."
::= { opticsIMCommonAlarms 220 }
 
-- End of OPTnm26383

-- Begin SNMPIDL-483 

opticsimAlarmLossOfPktSynchronizationRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Loss Of CEP Packet Synchronization alarm presence."
::= { opticsIMCommonAlarms 221 }

opticsimAlarmLossOfPktSynchronizationClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Loss Of CEP Packet Synchronization alarm presence."
::= { opticsIMCommonAlarms 222}

opticsimAlarmExcessiveMissingPktRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Excessive Missing CEP Packet alarm presence."
::= { opticsIMCommonAlarms 223 }

opticsimAlarmExcessiveMissingPktClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Excessive Missing CEP Packet alarm presence."
::= { opticsIMCommonAlarms 224}

-- End SNMPIDL-483 

-- Begin SNMPIDL-498 

opticsimAlarm1588TCFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the 1588 Transparent Clock Fail alarm presence."
::= { opticsIMCommonAlarms 225 }

opticsimAlarm1588TCFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the 1588 Transparent Clock Fail alarm presence."
::= { opticsIMCommonAlarms 226}

-- End SNMPIDL-498 

-- Begin SNMPIDL-502 

opticsimAlarmTrafficDownRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Traffic Down alarm presence."
::= { opticsIMCommonAlarms 227 }

opticsimAlarmTrafficDownClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Traffic Down alarm presence."
::= { opticsIMCommonAlarms 228}

opticsimAlarmTrafficLossRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Traffic Loss alarm presence."
::= { opticsIMCommonAlarms 229 }

opticsimAlarmTrafficLossClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Traffic Loss alarm presence."
::= { opticsIMCommonAlarms 230}

opticsimAlarmRxProblemRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of Rx Problem alarm presence."
::= { opticsIMCommonAlarms 231 }

opticsimAlarmRxProblemClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Rx Problem alarm presence."
::= { opticsIMCommonAlarms 232}

opticsimAlarmTxProblemRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Tx Problem alarm presence."
::= { opticsIMCommonAlarms 233 }

opticsimAlarmTxProblemClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Tx Problem alarm presence."
::= { opticsIMCommonAlarms 234 }

opticsimAlarmLagPortDownRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of LAG Port Down alarm presence."
::= { opticsIMCommonAlarms 235 }

opticsimAlarmLagPortDownClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the LAG Port Down alarm presence."
::= { opticsIMCommonAlarms 236 }

-- End SNMPIDL-502

-- Begin SNMPIDL-518

opticsimAlarmCKMRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Current Key Mismatch alarm presence."
::= { opticsIMCommonAlarms 237 }

opticsimAlarmCKMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Current Key Mismatch alarm presence."
::= { opticsIMCommonAlarms 238 }

opticsimAlarmNKMRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Next Key Mismatch alarm presence."
::= { opticsIMCommonAlarms 239 }

opticsimAlarmNKMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Next Key Mismatch alarm presence."
::= { opticsIMCommonAlarms 240 }

opticsimAlarmAesFipsFailureRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the AES engine Failure alarm presence."
::= { opticsIMCommonAlarms 241 }

opticsimAlarmAesFipsFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the AES engine Failure alarm presence."
::= { opticsIMCommonAlarms 242 }


opticsimAlarmSessionTimeoutRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the expiration (timeout) of the current manager session alarm presence."
::= { opticsIMCommonAlarms 243 }

opticsimAlarmSessionTimeoutClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the expiration (timeout) of the current manager session alarm presence."
::= { opticsIMCommonAlarms 244 }


-- Begin - SNMPIDL-513: F. Ruggi 

opticsimThresholdOutputPowerHighRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of warning condition of exceeding Threshold of transmitting Power too High."
::= { opticsIMCommonAlarms 245 }

opticsimThresholdOutputPowerHighClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of warning condition of exceeding Threshold of transmitting Power too High."
::= { opticsIMCommonAlarms 246 }

opticsimThresholdOutputPowerLowRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of warning condition of exceeding Threshold of transmitting Power too Low."
::= { opticsIMCommonAlarms 247 }

opticsimThresholdOutputPowerLowClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of warning condition of exceeding Threshold of transmitting Power too Low."
::= { opticsIMCommonAlarms 248 }

opticsimThresholdInputPowerHighRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of warning condition of exceeding Threshold of receiving Power too High."
::= { opticsIMCommonAlarms 249 }

opticsimThresholdInputPowerHighClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of warning condition of exceeding Threshold of receiving Power too High."
::= { opticsIMCommonAlarms 250 }

opticsimThresholdInputPowerLowRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of warning condition of exceeding Threshold of receiving Power too Low."
::= { opticsIMCommonAlarms 251 }

opticsimThresholdInputPowerLowClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of warning condition of exceeding Threshold of receiving Power too Low."
::= { opticsIMCommonAlarms 252 }

opticsimInputPowerOverloadRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of alarm condition of exceeding Threshold of receiving Power too High."
::= { opticsIMCommonAlarms 253 }

opticsimInputPowerOverloadClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of alarm condition of exceeding Threshold of receiving Power too High."
::= { opticsIMCommonAlarms 254 }

-- End - SNMPIDL-513: F. Ruggi 

opticsimAlarmESMRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Encryption State Mismatch alarm presence."
::= { opticsIMCommonAlarms 255 }

opticsimAlarmESMClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear the Encryption State Mismatch alarm presence."
::= { opticsIMCommonAlarms 256 }

opticsimAlarmKeyUnavailableRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the encryption key not available (or missing) alarm presence."
::= { opticsIMCommonAlarms 257 }

opticsimAlarmKeyUnavailableClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the encryption key not available (or missing) alarm presence."
::= { opticsIMCommonAlarms 258 }

-- End SNMPIDL-518 


opticsimFreeLicenseRunningRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the alarm to advice that the node is working in normal mode but without license key (free license). "
::= { opticsIMCommonAlarms 259 }

opticsimFreeLicenseRunningClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the alarm to advice that the node is working in normal mode but without license key (free license). "
::= { opticsIMCommonAlarms 260 }


opticsimFreeLicenseExpiredRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the alarm to advice that the node is working in degraded mode for license missing."
::= { opticsIMCommonAlarms 261 }

opticsimFreeLicenseExpiredClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the alarm to advice that the node is working in degraded mode for license missing."
::= { opticsIMCommonAlarms 262 }

opticsIMAlarmStolenStatusRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the alarm for the node entered on Stolen Status."
::= { opticsIMCommonAlarms 263 }

opticsIMAlarmStolenStatusClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the alarm for the node entered on Stolen Status."
::= { opticsIMCommonAlarms 264 }

opticsIMAlarmEthOAMUnexpectedMepRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports (Ethernet OAM Continuity Check) mismatch problems on CCM on receiving MEP."
::= { opticsIMCommonAlarms 265 }

opticsIMAlarmEthOAMUnexpectedMepClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the (Ethernet OAM Continuity Check) mismatch problems on CCM on receiving MEP."
::= { opticsIMCommonAlarms 266 }

opticsIMAlarmEthOAMMACStatusDefectRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the (Ethernet OAM Continuity Check) MAC Status defect."
::= { opticsIMCommonAlarms 267 }

opticsIMAlarmEthOAMMACStatusDefectClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the (Ethernet OAM Continuity Check) MAC Status defect."
::= { opticsIMCommonAlarms 268 }

opticsIMAlarmLogUploadFailureRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Log Upload Failure defect."
::= { opticsIMCommonAlarms 269 }

opticsIMAlarmLogUploadFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Log Upload Failure defect."
::= { opticsIMCommonAlarms 270 }

opticsIMAlarmIpsecPskMissingRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the IPSec PSK (Pre Secret Key) missing defect."
::= { opticsIMCommonAlarms 271 }

opticsIMAlarmIpsecPskMissingClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the IPSec PSK (Pre Secret Key) missing defect."
::= { opticsIMCommonAlarms 272 }

opticsIMAlarmIpsecTunnelSetupFailureRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the IPSec tunnel set-up failure defect."
::= { opticsIMCommonAlarms 273 }

opticsIMAlarmIpsecTunnelSetupFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the IPSec tunnel set-up failure defect."
::= { opticsIMCommonAlarms 274 }


opticsIMAlarmSecureSelfTestFailureRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the secure self-test failure defect."
::= { opticsIMCommonAlarms 275 }

opticsIMAlarmSecureSelfTestFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the secure self-test failure  defect."
::= { opticsIMCommonAlarms 276 }

opticsIMAlarmEthOAMUnexpectedCcmConnectivityRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the ETH OAM Unexpected CCM conectivity defect."
::= { opticsIMCommonAlarms 277 }

opticsIMAlarmEthOAMUnexpectedCcmConnectivityClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the ETH OAM Unexpected CCM conectivity defect."
::= { opticsIMCommonAlarms 278 }

opticsIMAlarmSecureModeMismatchRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Secure mode mismatch defect."
::= { opticsIMCommonAlarms 279 }

opticsIMAlarmSecureModeMismatchClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Secure mode mismatch defect."
::= { opticsIMCommonAlarms 280 }

opticsIMAlarmSWDLConditionalSelfTestFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Sw Download Conditional Self test defect."
::= { opticsIMCommonAlarms 281 }

opticsIMAlarmSWDLConditionalSelfTestFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Sw Download Conditional Self test defect."
::= { opticsIMCommonAlarms 282 }


opticsIMAlarmCRNGConditionalSelfTestFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Conditional Random Number Generator (CRNG)  Self test defect."
::= { opticsIMCommonAlarms 283 }

opticsIMAlarmCRNGConditionalSelfTestFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Conditional Random Number Generator (CRNG)  Self test defect."
::= { opticsIMCommonAlarms 284 }


opticsIMAlarmUpdateIPSecKeysFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Update of IP Sec Key Fail alarm."
::= { opticsIMCommonAlarms 285 }

opticsIMAlarmUpdateIPSecKeysFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Update of IP Sec Key Fail alarm."
::= { opticsIMCommonAlarms 286 }

opticsIMAlarmZeroizeIPSecKeysFailRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Zeroize of the IP Sec Key Fail alarm."
::= { opticsIMCommonAlarms 287 }

opticsIMAlarmZeroizeIPSecKeysFailClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Zeroize of the IP Sec Key Fail alarm."
::= { opticsIMCommonAlarms 288 }

opticsIMAlarmVESListenerConnectionFailureRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the alarm for problems to send VES events to Listener Collector ."
::= { opticsIMCommonAlarms 289 }

opticsIMAlarmVESListenerConnectionFailureClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the alsrm for problems to send VES events to Listener Collector ."
::= { opticsIMCommonAlarms 290 }

opticsIMAlarmMissingDiversityAlignConfRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the alarm for problems to send VES events to Listener Collector ."
::= { opticsIMCommonAlarms 291 }

opticsIMAlarmMissingDiversityAlignConfClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the alsrm for problems to send VES events to Listener Collector ."
::= { opticsIMCommonAlarms 292 }

opticsIMAlarmACMDegradeRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the alarm for ACM Degrade, when the max Modulation is not reached for a specific time period ."
::= { opticsIMCommonAlarms 293 }

opticsIMAlarmACMDegradeClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the alarm for ACM Degrade."
::= { opticsIMCommonAlarms 294 }


opticsIMAlarmLocalAutoTxMuteRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the alarm for auto mute."
::= { opticsIMCommonAlarms 295 }

opticsIMAlarmLocalAutoTxMuteClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the alarm for auto mute."
::= { opticsIMCommonAlarms 296 }

opticsIMAlarmLossOfContinuityRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the raise of the Loss Of Continuity alarm on the resource specified."
::= { opticsIMCommonAlarms 297 }

opticsIMAlarmLossOfContinuityClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the clear of the Loss Of Continuity alarm on the resource specified."
::= { opticsIMCommonAlarms 298 }

opticsIMAlarmPowerSavingActiveRaise NOTIFICATION-TYPE
  OBJECTS {
    tsdimEventObjectClassIdentifier,
    tsdimEventObjectInstanceIdentifier,
    tsdimEventNotificationId,
    tsdimEventTime,
    tsdimAlarmSeverity,
    tsdimAlarmSpecProblem,
    opticsIMAdditionalText,
    opticsIMAlarmType
  }
  STATUS current
  DESCRIPTION 
    "This notification reports the activation of the Power Saving on the resource specified."
::= { opticsIMCommonAlarms 299 }

opticsIMAlarmPowerSavingActiveClear NOTIFICATION-TYPE
  OBJECTS {
    tsdimEventObjectClassIdentifier,
    tsdimEventObjectInstanceIdentifier, 
    tsdimEventNotificationId,
    tsdimEventTime,
    tsdimAlarmSeverity,
    tsdimAlarmSpecProblem,
    opticsIMAdditionalText,
    opticsIMAlarmType
  }
  STATUS current
  DESCRIPTION
    "This notification reports the deactivation of the Power Saving on the resource specified."
::= { opticsIMCommonAlarms 300 }


-- Begin - TSDnm96257: G.Gallina 

opticsIMCapabilityProfileTable OBJECT-TYPE
      SYNTAX SEQUENCE OF OpticsIMCapabilityProfileEntry
      MAX-ACCESS not-accessible
      STATUS current
      DESCRIPTION
        "This table contains a list of capability."
::= { tsdimSnmpNEMibObject 56 }

opticsIMCapabilityProfileEntry OBJECT-TYPE
  SYNTAX OpticsIMCapabilityProfileEntry
  MAX-ACCESS not-accessible
  STATUS current
  DESCRIPTION
    "An entry of the opticsIMCapabilityProfileTable."
  INDEX { opticsIMCapabilityProfileProfIndex, opticsIMCapabilityProfileCapIndex }
::= { opticsIMCapabilityProfileTable 1 }

OpticsIMCapabilityProfileEntry ::=
  SEQUENCE { 
    opticsIMCapabilityProfileProfIndex    OpticsIMcapabilityProfileIndex,
    opticsIMCapabilityProfileCapIndex     OpticsIMCapabilityIndex,
    opticsIMCapabilityProfileCapUserLabel OpticsIMUserLabel,
    opticsIMCapabilityProfileCapInfo      OCTET STRING
}

opticsIMCapabilityProfileProfIndex OBJECT-TYPE
  SYNTAX OpticsIMcapabilityProfileIndex
  MAX-ACCESS not-accessible
  STATUS current
  DESCRIPTION
    "The value of this object is equal to opticsIMcapabilityProfileProfIndex 
     in the opticsIMCapabilityProfileTable."
  ::= { opticsIMCapabilityProfileEntry 1 }

opticsIMCapabilityProfileCapIndex OBJECT-TYPE
  SYNTAX OpticsIMCapabilityIndex
  MAX-ACCESS not-accessible
  STATUS current
  DESCRIPTION
    "The value of this object is equal to opticsIMCapabilityProfileCapIndex in 
     the opticsIMCapabilityProfileTable."
::= { opticsIMCapabilityProfileEntry 2 }

opticsIMCapabilityProfileCapUserLabel OBJECT-TYPE
  SYNTAX OpticsIMUserLabel
  MAX-ACCESS read-only
  STATUS current
  DESCRIPTION
    "Name of the capability. List of possible values is defined in reference 
     document"
::= { opticsIMCapabilityProfileEntry 3 }

opticsIMCapabilityProfileCapInfo OBJECT-TYPE
  SYNTAX OCTET STRING
  MAX-ACCESS read-only
  STATUS current
  DESCRIPTION
    "Information about capability. List of possible values is defined in 
     reference document"
::= { opticsIMCapabilityProfileEntry 4 }

-- End - TSDnm96257: G.Gallina 

--- Begin - OPTnm02313 : Y.Wang

-- opticsIMSwitch Table --
   opticsIMSwitchTable OBJECT-TYPE
      SYNTAX        SEQUENCE OF OpticsIMSwitchEntry
      MAX-ACCESS    not-accessible
      STATUS        current
      DESCRIPTION
           "This table contains objects for each Switch Instannce ."
      ::= { tsdimSnmpNEMibObject 57 }

   opticsIMSwitchEntry OBJECT-TYPE
      SYNTAX        OpticsIMSwitchEntry
      MAX-ACCESS    not-accessible
      STATUS        current
      DESCRIPTION
           "An entry in this table represents an Ethernet Switch instance. It is autocreated/autodeleted by agent
	    when a card is provisioned with switch instance"
      INDEX { opticsIMSwitchIndex }
      ::= { opticsIMSwitchTable 1 }

   OpticsIMSwitchEntry ::= SEQUENCE {
         opticsIMSwitchIndex                   INTEGER,   
         opticsIMSwitchID                      INTEGER,      
         opticsIMSwitchOperationMode	       INTEGER,
         opticsIMSwitchEthOamBridgeMAC         MacAddress,
         opticsIMSwitchEthOamLbmReplyTimeout   INTEGER, 
         opticsIMSwitchEthOamLbmTxInterval     INTEGER,
         opticsIMSwitchLinkOAMLogMinInterval   INTEGER,
         opticsIMSwitchPBProfile       	       INTEGER,
         opticsIMSwitchTpAgingTime             Integer32,
         opticsIMSwitchTpLearnedEntryDiscards  Counter32,
         opticsIMSwitchSTPType                 INTEGER,
         opticsIMSwitchCfmMaTableNextIndex     Gauge32,
         opticsIMSwitchLocation                INTEGER,
         opticsIMSwitchBridgeFilteringMode     INTEGER,
         opticsIMSwitchUserLabel     	       OpticsIMUserLabel       
        }
  opticsIMSwitchIndex OBJECT-TYPE
      SYNTAX        INTEGER
      MAX-ACCESS    not-accessible
      STATUS        current
      DESCRIPTION
           "The index for switch Table."
      ::= { opticsIMSwitchEntry 1 }

   opticsIMSwitchID OBJECT-TYPE
      SYNTAX        INTEGER
      MAX-ACCESS    read-only
      STATUS        current
      DESCRIPTION
           "Uniquely identifies a Ethernet switch instance , the initial value starts from 0 ."
      ::= { opticsIMSwitchEntry 2 }

   opticsIMSwitchOperationMode OBJECT-TYPE
      SYNTAX        INTEGER {
                    none(1),
	                bridge8021D(2),
	                bridge8021Q(3),
	                bridge8021ad(4),
	                bridge8021ah(5),
	                bridge8021adah(6)
	                }
	  MAX-ACCESS    read-write
      STATUS        current
      DESCRIPTION
           "Indicates what types of mechanism this Bridge perfoms.
 	        none (1) This NE cannot perform any bridge mechanism
 	        bridge8021D (2) This Bridge performs 802.1D mechanism and can not support VLAN
 	        bridge8021Q (3) This Bridge performs 802.1Q mechanism
 	        bridge8021ad (4) This Bridge performs 802.1ad mechanism. 
 	        The default value is bridge8021ad(4)."
      ::= { opticsIMSwitchEntry 3 }  
      
   opticsIMSwitchEthOamBridgeMAC OBJECT-TYPE
      SYNTAX        MacAddress
      MAX-ACCESS    read-only
      STATUS        current
      DESCRIPTION
           "The MAC address of the Bridge that is used as ETH OAM messages MAC SA."
      ::= { opticsIMSwitchEntry 4 }

  opticsIMSwitchEthOamLbmReplyTimeout OBJECT-TYPE
      SYNTAX        INTEGER 
      MAX-ACCESS    read-write
      STATUS        current
      DESCRIPTION
           "The LBR timeout after the corresponding LBM has been sent. It is
 	        measured in seconds in the range [1-30], with default =5."
      ::= { opticsIMSwitchEntry 5 }


  opticsIMSwitchEthOamLbmTxInterval OBJECT-TYPE
      SYNTAX        INTEGER 
      MAX-ACCESS    read-write
      STATUS        current
      DESCRIPTION
           "The interval between two LBM  frames sent. It is
 	        measured in 100 milli-second in the range [1-100]*100 ms, with default = 1second."
      ::= { opticsIMSwitchEntry 6 }

  opticsIMSwitchLinkOAMLogMinInterval OBJECT-TYPE
      SYNTAX         INTEGER (1..60) 
      MAX-ACCESS    read-write
      STATUS        current
      DESCRIPTION
           "This parameter defines the granularity window (sec) for the
 	        logging of LinkOAM event in the dot3OamEventLogTable.
 	        If more events of the same type are to be logged in this
 	        table in the window specified by this object, only the
 	        first one shall be logged.
 	        The default value is product specific ."
      ::= { opticsIMSwitchEntry 7 }

  opticsIMSwitchPBProfile OBJECT-TYPE
    SYNTAX     INTEGER
    MAX-ACCESS read-write
    STATUS     current
    DESCRIPTION
        "This object defines 'on per Switch basis' admitted Provider
         Bridge profiles with below values:
         - 5P3D (1) - Default value,
         - 8P0D (2),
         - 7P1D (3),
         - 6P2D (4),
         - Customer-defined profile1 (5) whose support is NE product specific"
     ::= { opticsIMSwitchEntry 8 }
 
   opticsIMSwitchTpAgingTime OBJECT-TYPE
      SYNTAX        Integer32  
      MAX-ACCESS    read-write
      STATUS        current
      DESCRIPTION
           "The timeout period in seconds (Range: 10..1000000) for 
            aging out dynamically learned forwarding information.
            802.1D-1998 recommends a default of 300 seconds.
            A value of 0x7FFFFFFF  indicates aging disabled."
      ::= { opticsIMSwitchEntry 9 }
    
   opticsIMSwitchTpLearnedEntryDiscards OBJECT-TYPE
      SYNTAX        Counter32  
      MAX-ACCESS    read-only
      STATUS        current
      DESCRIPTION
           "The total number of Forwarding Database entries, which
            have been or would have been learnt, but have been
            discarded due to a lack of space to store them in the
            Forwarding Database.  If this counter is increasing, it
            indicates that the Forwarding Database is regularly
            becoming full (a condition which has unpleasant
            performance effects on the subnetwork).  If this counter
            has a significant value but is not presently increasing,
            it indicates that the problem has been occurring but is
            not persistent."
      ::= { opticsIMSwitchEntry 10 }
      
   opticsIMSwitchSTPType OBJECT-TYPE
      SYNTAX        INTEGER { 
                    manualDisable(1),
                    stp(2),
	                rstp(3),
	                pervlanrstp(4),
	                mstp(5),
	                rstpPlus(6),
	                mstpPlus(7)
                    } 
      MAX-ACCESS    read-write
      STATUS        current
      DESCRIPTION
           "STP Type configuration: 	
 	       - manualDisable (1) is used to disable the protocol for the bridge 	
 	       - stp(2) is used to enable STP and synchronously the Rapid STP
 	         is disabled 	
 	       - rstp(3) is used to enable Rapid STP and synchronously STP is
 	         disabled
           - pervlanrstp(4) is used to enable per-VLAN RSTP 	
 	       - mstp(5) is used to enable RSTP-based MSTP
 	       - rstpPlus (6) is used to enable further optimization for RSTP
 	       - mstpPlus (7) is used to enable further optimization for MSTP.
 	       The default value is product specific . "
      ::= { opticsIMSwitchEntry 11 }

   opticsIMSwitchCfmMaTableNextIndex OBJECT-TYPE
      SYNTAX        Gauge32 (0..4294967295) 
      MAX-ACCESS    read-only
      STATUS        current
      DESCRIPTION
           "Value to be used as the index of the MA table when the
        management entity wants to create a new row in the table."
      ::= { opticsIMSwitchEntry 12 }
                    
  opticsIMSwitchLocation OBJECT-TYPE
      SYNTAX        INTEGER 
      MAX-ACCESS    read-only
      STATUS        current
      DESCRIPTION
           "it will be master slot in stack mode.
           RRSSBBDD
           RR- Rack
           SS- Subrack
           BB- Slot
           DD- Drawer."
      ::= { opticsIMSwitchEntry 13 }

  opticsIMSwitchBridgeFilteringMode OBJECT-TYPE
      SYNTAX      INTEGER {
                  ivl(1),
                  svl(2),
                  hybrid (3)
                  }  
      MAX-ACCESS    read-write
      STATUS        current
      DESCRIPTION
           "The Type of VLAN learning mode.When the object value is modified, the static
           fid-vlan mappings and static unicast entries need to be reconfigured. Static 
           unicast configurations associated with old fid will get deleted.
           The default value is ivl(1) ."
      ::= { opticsIMSwitchEntry 14 }
	  
   opticsIMSwitchUserLabel OBJECT-TYPE
      SYNTAX        OpticsIMUserLabel
      MAX-ACCESS    read-write
      STATUS        current
      DESCRIPTION
           "The canonical name assigned to Switch Instance."
      ::= { opticsIMSwitchEntry  15 }


-- opticsIMSwitchPortTable ----
   
   opticsIMSwitchPortTable OBJECT-TYPE
      SYNTAX SEQUENCE OF OpticsIMSwitchPortEntry
      MAX-ACCESS not-accessible
      STATUS current
      DESCRIPTION 
           " This table contains Ethernet switch ports associated to 
             each Ethernet switch instance."
      ::= { tsdimSnmpNEMibObject 58  }

   opticsIMSwitchPortEntry OBJECT-TYPE
      SYNTAX OpticsIMSwitchPortEntry
      MAX-ACCESS not-accessible
      STATUS current
      DESCRIPTION
        "An entry in this table represents an switch port.
		 Being read-only table, it is autocreated by agent
		 when an instance within opticsIMSwitchEntry is allocated
		 with the port associated"
      INDEX { opticsIMSwitchIndex,opticsIMSwitchPortIndex }
      ::= { opticsIMSwitchPortTable 1 }

   OpticsIMSwitchPortEntry ::= SEQUENCE {
       opticsIMSwitchPortIndex     	 InterfaceIndex,
       opticsIMSwitchPortMapStatus       INTEGER
        }
 
    opticsIMSwitchPortIndex OBJECT-TYPE
      SYNTAX        InterfaceIndex
      MAX-ACCESS    not-accessible
      STATUS        current
      DESCRIPTION
           "The ifIndex value of the interface."
      ::= { opticsIMSwitchPortEntry 1 }

   opticsIMSwitchPortMapStatus OBJECT-TYPE
      SYNTAX        INTEGER
      MAX-ACCESS    read-only
      STATUS        current
      DESCRIPTION
           "Switch Port Entry status. This object is always equal to 0.
            It is a dummy object needed to have something to retrieve"
      ::= { opticsIMSwitchPortEntry 2  }
     
-- End of opticsIMSwitchPortTable
-- End OPTnm02313 : Y.Wang


-- Begin OPTnm07660: D.Spreafico

-- opticsIMTACACSServerManagement 

opticsIMTACACSServerManagement OBJECT IDENTIFIER ::= { tsdimSnmpNEMibObject 59 }


opticsIMTACACSServerTable OBJECT-TYPE
  SYNTAX SEQUENCE OF OpticsIMTACACSServerEntry
  MAX-ACCESS not-accessible
  STATUS current
  DESCRIPTION
    "The TACACS server table.
     This table contains all the TACACS servers configured on the NE."
::= { opticsIMTACACSServerManagement 1 }

opticsIMTACACSServerEntry OBJECT-TYPE
  SYNTAX OpticsIMTACACSServerEntry
  MAX-ACCESS not-accessible
  STATUS current
  DESCRIPTION
    "Entry is automatically created by Agent when a new TACACS server is configured on NE."
  INDEX { opticsIMTACACSServerIndex }
::= { opticsIMTACACSServerTable 1 }

OpticsIMTACACSServerEntry ::= SEQUENCE {
  opticsIMTACACSServerIndex Integer32,
  opticsIMTACACSServerFailureCount Integer32
}

opticsIMTACACSServerIndex OBJECT-TYPE
  SYNTAX Integer32
  MAX-ACCESS not-accessible
  STATUS current
  DESCRIPTION
    "This is the index for the TACACS Server table."
::= { opticsIMTACACSServerEntry 1 }

opticsIMTACACSServerFailureCount OBJECT-TYPE
  SYNTAX Integer32
  MAX-ACCESS read-only
  STATUS current
  DESCRIPTION
    "This is the number of the tentative to access to this TACACS server with negative result."
::= { opticsIMTACACSServerEntry 2 }

opticsIMTACACSLastServerUsed OBJECT-TYPE
  SYNTAX Integer32
  MAX-ACCESS read-only
  STATUS current
  DESCRIPTION
    "This object reports the opticsIMTACACSServerIndex value of the last TACACS server reachable 
     and used for Authentication/Authotization/Accounting access to the NE."
::= { opticsIMTACACSServerManagement 2 }

opticsIMTACACSAuthentication OBJECT-TYPE
  SYNTAX INTEGER {
    localDB (1), 
    remoteTACACSServer (2)
  }
  MAX-ACCESS read-only
  STATUS current
  DESCRIPTION
    "This object defines the actual user credential repository used for Authentication/Authotization/Accounting
     access to the NE."
::= { opticsIMTACACSServerManagement 3 }

-- End OPTnm07660: D.Spreafico


-- Begin OPTnm08359: D.Spreafico

-- opticsIMRateLimitingProfile

opticsIMRateLimitingProfileTable OBJECT-TYPE
  SYNTAX SEQUENCE OF OpticsIMRateLimitingProfileEntry
  MAX-ACCESS not-accessible
  STATUS current
  DESCRIPTION 
    "This table contains objects for a rate limiting profile of a NE interface."
::= { tsdimSnmpNEMibObject 60 }

opticsIMRateLimitingProfileEntry OBJECT-TYPE
  SYNTAX OpticsIMRateLimitingProfileEntry
  MAX-ACCESS not-accessible
  STATUS current
  DESCRIPTION
    "An entry references, on port basis, a rate limiting profile."
  INDEX { ifIndex, opticsIMRLProfileVlan, opticsIMRLProfilePCP }
::= { opticsIMRateLimitingProfileTable 1 }

OpticsIMRateLimitingProfileEntry ::= SEQUENCE {
  opticsIMRLProfileVlan                   Unsigned32,
  opticsIMRLProfilePCP                    INTEGER,
  opticsIMRLProfileCommittedRate          Gauge32,
  opticsIMRLProfileCommittedBurstSize     Gauge32,
  opticsIMRLProfileRowStatus              RowStatus
  }

opticsIMRLProfileVlan    OBJECT-TYPE
  SYNTAX      Unsigned32 (0..4097)
  MAX-ACCESS  read-write
  STATUS      current
  DESCRIPTION
     "The VLAN value associated to this profile. 
        Values between 0 to 4095 indicate the actual VLAN field
        value.
        A value of 4096 indicates that the object refer to  
        untagged frames, i.e. frames without 802.1Q field. 
        A value of 4097 indicates that the VLAN field is not  
        relevant, both if valued and if not present."
::= { opticsIMRateLimitingProfileEntry 1 }

opticsIMRLProfilePCP     OBJECT-TYPE
  SYNTAX   INTEGER
        {
        pri000(0),
        pri001(1),
        pri010(2),
        pri011(3),
        pri100(4),
        pri101(5),
        pri110(6),
        pri111(7),
        untagged(8),
        dontCare(9)
        }
  MAX-ACCESS  read-write
  STATUS      current
  DESCRIPTION
    "The PCP value associated to this profile."
::= { opticsIMRateLimitingProfileEntry 2 }

opticsIMRLProfileCommittedRate          OBJECT-TYPE
  SYNTAX      Gauge32
  MAX-ACCESS  read-write
  STATUS      current
  DESCRIPTION
    "The committed rate associated to this profile."
::= { opticsIMRateLimitingProfileEntry 3 }

opticsIMRLProfileCommittedBurstSize     OBJECT-TYPE
  SYNTAX      Gauge32
  MAX-ACCESS  read-write
  STATUS      current
  DESCRIPTION
    "The committed size associated to this profile."
::= { opticsIMRateLimitingProfileEntry 4 }

opticsIMRLProfileRowStatus              OBJECT-TYPE
  SYNTAX      RowStatus     
  MAX-ACCESS  read-write
  STATUS      current
  DESCRIPTION
    "For creating and deleting this row."
::= { opticsIMRateLimitingProfileEntry 5 }

-- End OPTnm08359: D.Spreafico

-- END
   

-- TSDIM-SNMPNE-MC DEFINITIONS ::= BEGIN
--     IMPORTS
--     MODULE-IDENTITY, OBJECT-TYPE FROM SNMPv2-SMI
--     MODULE-COMPLIANCE, NOTIFICATION-GROUP, OBJECT-GROUP FROM SNMPv2-CONF
--     tsdimBasicMC FROM TSDIM-BASICREG-MIB;

-- tsdimSnmpNEMCCompl

-- tsdimSnmpNEMCCompl MODULE-IDENTITY
-- LAST-UPDATED "200201250000Z"
-- ORGANIZATION "Alcatel TND"
-- CONTACT-INFO "Alcatel TND"
-- DESCRIPTION
--      "New object: NE Configuration Type "
-- REVISION "200009290000Z"
-- DESCRIPTION
--     "Generic objects, such as opticsIMSdhIfTable, tsdimIf..., 
--      Tsf and Plm alarms, have been added to this MIB and deleted 
--      from TSDIM-TRS-MIB."
-- REVISION "200007010000Z"
-- DESCRIPTION
--      "They have been moved the following functionalities:
--       - IP routing,
--       - Polling management."
-- REVISION "200002290000Z"
-- DESCRIPTION
--      "They have been added the following functionalities:
--       - IP routing,
--       - Support managemeng and
--       - Polling management.
--       Moreover it has been re-arranged the object description clauses
--       and the registration numbers in order to have an 
--       aggregation of objects based on functionalities."
-- REVISION "9910210000Z"
-- DESCRIPTION
--     "Initial Release TSD-IM SNMP NE MODULE COMPLIANCE"
-- ::= { tsdimSnmpNEMCConf 1 }

tsdimSnmpNEMCConf       OBJECT IDENTIFIER ::= { tsdimBasicMC 2 }
tsdimSnmpNEMCCompl      OBJECT IDENTIFIER ::= { tsdimSnmpNEMCConf 1 }
tsdimSnmpNEMCGroup      OBJECT IDENTIFIER ::= { tsdimSnmpNEMCConf 2 }

tsdimSnmpNEMc MODULE-COMPLIANCE
    STATUS current
    DESCRIPTION
        "This module compliance describes a set of objects required
         for TSD-IM SNMP Agent implementation. These objects are
         defined inside tsdimSnmpNEMib"

    MODULE -- tsdimSnmpNEMib

MANDATORY-GROUPS { tsdimSnmpNEGroup,
                  opticsIMIfExtGroup,
                  opticsIMAlarmGroup,
                  opticsIMTptCoordinatorGroup }

GROUP tsdimLacSupportGroup
    DESCRIPTION
        "This group contains the Local Access Control information"

GROUP opticsIMACDGroup
    DESCRIPTION
        "This group contains the objects used to assign resources at NE
         level."

GROUP opticsIMNeConfigurationGroup
    DESCRIPTION
        "This group describes the objects needed for NE configuration. "

GROUP opticsIMSnmpNETimeGroup
    DESCRIPTION
        "This group describes the objects needed for NE time management,
         when NTP is not supported."

GROUP opticsIMNTPGroup
    DESCRIPTION
        "This group describes the objects needed for NTP management."

GROUP opticsIMOptAlarmGroup
    DESCRIPTION
        "This group describes the notifications used by
         at least between two different technologies."

GROUP opticsIMNePMCollectionGroup
    DESCRIPTION
"This group describes the objects needed for NE PM Collection. "

::= { tsdimSnmpNEMCCompl 1 }

-- Units of conformance

tsdimSnmpNEGroup OBJECT-GROUP
    OBJECTS { tsdimSnmpAgtIpAddress,
        tsdimNeInstallationType,
        tsdimSnmpAgtIpMask,
        tsdimSnmpAgtUdpPort,
        tsdimInfoModelVersionMajor,
        tsdimInfoModelVersionMinor,
        tsdimInfoModelVersionMaintenance,
        tsdimSdhNeLabel,
        tsdimBoardPosition,
        opticsimEpsConfStatus,
        opticsimEpsActiveRole,
        opticsimMaskNamingRule,
	opticsimSwPackageProfile,
	opticsimSwPackageProfileRequested }
    STATUS current
    DESCRIPTION
        "This group describes the objects needed for the SNMP NE
         Configuration."
::= { tsdimSnmpNEMCGroup 1 }

tsdimLacSupportGroup OBJECT-GROUP
    OBJECTS { tsdimLacState,
        tsdimLacNoResponseTimeOutPeriod }
    STATUS current
    DESCRIPTION
        "This group describes the objects needed for Lac Configuration."
::= { tsdimSnmpNEMCGroup 6 }

opticsIMACDGroup OBJECT-GROUP
    OBJECTS { opticsIMNeOwnsByMgr}
    STATUS current
    DESCRIPTION
        "This group describes the objects needed for the
         resource assignment functionality."
::= { tsdimSnmpNEMCGroup 7 }

opticsIMIfExtGroup OBJECT-GROUP
    OBJECTS { tsdimIfUnderlieLayer,
        tsdimIfOwnsByMgr,
        tsdimIfAsapIndex,
        opticsIMIfBridgeBasePort }
    STATUS current
    DESCRIPTION
        "A collection of objects providing extensions for the
         configuration of an interface."
::= { tsdimSnmpNEMCGroup 8 }

opticsIMAlarmGroup NOTIFICATION-GROUP
    NOTIFICATIONS{ tsdimAlarmPlmRaise,
        tsdimAlarmPlmClear,
        tsdimAlarmTsfRaise,
        tsdimAlarmTsfClear }
    STATUS current
    DESCRIPTION
        "This group describes the alarm  notifications"
::= { tsdimSnmpNEMCGroup 9 }

opticsIMTptCoordinatorGroup OBJECT-GROUP
    OBJECTS { opticsIMSdhIfSpeed,
              opticsIMSdhIfUnderlieLayer,
              opticsIMSdhIfType,
              opticsIMSdhIfVcType }
    STATUS current
    DESCRIPTION
        "A collection of objects providing configuration information
         for the TPT Coordinator objects."
::= { tsdimSnmpNEMCGroup 10 }

opticsIMNeConfigurationGroup OBJECT-GROUP
     OBJECTS { opticsIMNeConfigurationType,
               opticsIMNeConfigurationTypeId,
               opticsIMAllowedNeConfigurationType,
               opticsIMMarket,
               opticsIMNeEquipmentName,
               opticsIMAllowedNePeripheralType,
               opticsIMAllowedNePeripheralConfiguration,
               opticsIMNeTrsDirectionConfigurationId,
               opticsIMNeTrsDirectionMaxCapacity,
               opticsIMNeTrsDirectionRole,
               opticsIMNeDirectionPeripheralId,
               opticsIMNeDirectionPeripheralType,
               opticsIMNeDirectionPeripheralConfiguration,
               opticsIMNeCompositionConfigurationId,
               opticsIMNeCompositionConfigurationType,
               opticsIMNeCompositionRowStatus,
               opticsIMNeCompositionIndexNext 
                 }
     STATUS current
     DESCRIPTION
         " This group describes the objects needed for NE configuration. "
::= {  tsdimSnmpNEMCGroup 11 }

opticsIMSnmpNETimeGroup OBJECT-GROUP
    OBJECTS { opticsIMExternalTime }
    STATUS current
    DESCRIPTION
        "This group describes the object used to manage the NE time, when
         NTP is not supported."
::= { tsdimSnmpNEMCGroup 12 }

opticsIMNTPGroup OBJECT-GROUP
    OBJECTS { opticsIMNTPStatus,
              opticsIMMainNTPServerAddress,
              opticsIMSpareNTPServerAddress,
              opticsIMNTPServersReachabilityStatus }
    STATUS current
    DESCRIPTION
        "This group describes the objects related to the NTP management."
::= { tsdimSnmpNEMCGroup 13 }

opticsIMOptAlarmGroup NOTIFICATION-GROUP
    NOTIFICATIONS{ opticsIMAlarmLossOfSignalRaise,
                   opticsIMAlarmLossOfSignalClear,
                   opticsIMAlarmLossOfFrameRaise,
                   opticsIMAlarmLossOfFrameClear,
                   opticsIMAlarmAisRaise,
                   opticsIMAlarmAisClear,
                   opticsIMAlarmTransmitterFailureRaise,
                   opticsIMAlarmTransmitterFailureClear,
                   opticsIMAlarmTransmitterDegradedRaise,
                   opticsIMAlarmTransmitterDegradedClear,
                   opticsIMAlarmRemoteDefectIndicationRaise,
                   opticsIMAlarmRemoteDefectIndicationClear,
                   opticsIMAlarmCableLOSRaise,
                   opticsIMAlarmCableLOSClear,
                   opticsIMAlarmRxLOSRaise,
                   opticsIMAlarmRxLOSClear,
                   opticsIMAlarmRxFailRaise,
                   opticsIMAlarmRxFailClear,
                   opticsIMAlarmDemLOSRaise,
                   opticsIMAlarmDemLOSClear,
                   opticsIMAlarmDemFailRaise,
                   opticsIMAlarmDemFailClear,
                   opticsIMAlarmModLOSRaise,
                   opticsIMAlarmModLOSClear,
                   opticsIMAlarmModFailRaise,
                   opticsIMAlarmModFailClear,
                   opticsIMAlarmTxLOSRaise,
                   opticsIMAlarmTxLOSClear,
                   opticsIMAlarmTxFailRaise,
                   opticsIMAlarmTxFailClear,
                   opticsIMAlarmTCARaise,
                   opticsIMAlarmTCAClear,
                   opticsIMAlarmUnavailableTimeRaise,
                   opticsIMAlarmUnavailableTimeClear,
                   opticsIMAlarmTsfRaise,
                   opticsIMAlarmTsfClear,
                   opticsIMAlarmPlmRaise,
                   opticsIMAlarmPlmClear,
                   opticsIMAlarmUruRaise,
                   opticsIMAlarmUruClear,
                   opticsIMAlarmLAPDFailRaise,
                   opticsIMAlarmLAPDFailClear,
                   opticsIMAlarmLossOfAlignmentRaise,
                   opticsIMAlarmLossOfAlignmentClear,
                   opticsIMAlarmPPPFailRaise,
                   opticsIMAlarmPPPFailClear,
                   opticsIMAlarmRemoteNEFailureRaise,
                   opticsIMAlarmRemoteNEFailureClear,
                   opticsimGfpAlarmGtmRaise,
                   opticsimGfpAlarmGtmClear,
                   opticsimDAAlarmDACMRaise,
                   opticsimDAAlarmDACMClear,
                   opticsimClientSignalFailRaise,
                   opticsimClientSignalFailClear,
                   opticsIMAlarmLossOfPointerRaise,
                   opticsIMAlarmLossOfPointerClear,
                   opticsIMAlarmLossOfMultiframeRaise,
                   opticsIMAlarmLossOfMultiframeClear,
                   opticsIMAlarmSequenceMismatchRaise,
                   opticsIMAlarmSequenceMismatchClear,
                   opticsIMAlarmServerSignalFailRaise,
                   opticsIMAlarmServerSignalFailClear,
                   opticsIMAlarmUnequippedRaise,
                   opticsIMAlarmUnequippedClear,
                   opticsIMAlarmExstensionHeaderMismatchRaise,
		   opticsIMAlarmExstensionHeaderMismatchClear,
		   opticsIMAlarmUserPayloadMismatchRaise,
		   opticsIMAlarmUserPayloadMismatchClear,
                   opticsIMAlarmDegradeRaise,
                   opticsIMAlarmDegradeClear,
                   opticsimAlarmServerSignalIngrFailRaise,
                   opticsimAlarmServerSignalIngrFailClear,
                   opticsimAlarmServerSignalEgreFailRaise,
                   opticsimAlarmServerSignalEgreFailClear,

                   opticsimAlarmTrafficDisableRaise,
                   opticsimAlarmTrafficDisableClear,
                   opticsimAlarmEthOAMLossOfContinuityRaise,
                   opticsimAlarmEthOAMLossOfContinuityClear,
                   opticsimAlarmEthOAMMisMergeConditionRaise,
                   opticsimAlarmEthOAMMisMergeConditionClear,
                   opticsimAlarmEthOAMUnexpectedMepIdRaise,
                   opticsimAlarmEthOAMUnexpectedMepIdClear,
                   opticsimAlarmEthOAMUnexpectedPeriodRaise,
                   opticsimAlarmEthOAMUnexpectedPeriodClear,
                   opticsimAlarmEthOAMUnexpectedLevelRaise,
                   opticsimAlarmEthOAMUnexpectedLevelClear,
                   opticsimAlarmEthOAMRDIRaise,
                   opticsimAlarmEthOAMRDIClear,
                   opticsimAlarmEthOAMUNPrRaise,
		           opticsimAlarmEthOAMUNPrClear,
		           opticsimAlarmEthPNACRaise,
		           opticsimAlarmEthPNACClear
                   }
    STATUS current
    DESCRIPTION
        "This group describes the alarm  notifications"
::= { tsdimSnmpNEMCGroup 14 }


-- opticsIMNePMCollectionGroup
opticsIMNePMCollectionGroup OBJECT-GROUP
    OBJECTS { opticsIMNePMCollectionStatus,
              opticsIMNePMActivateCollection,
              opticsIMNePMTimePeriodCollection }
    STATUS current
    DESCRIPTION
      " This group describes the objects needed for NE PM Collection. "
::= { tsdimSnmpNEMCGroup 15 }


END
